;;; acaddoc.lsp - with YS-Tools test (write to desktop)
(defun AA-load-local-file (file-name / file-path)
  (setq file-path (findfile file-name))
  (if file-path
    (load file-path nil)
  )
)
(AA-load-local-file "AA_main.lsp")

;;; YS-Tools Auto-Load
(if (findfile "YS-Tools\\YS-Tools.lsp")
  (progn
    (load "YS-Tools\\YS-Tools.lsp")
    (princ)
  )
)

;;; TEST: write to desktop
(setq __jtf (open (strcat (getenv "USERPROFILE") "\\Desktop\\ys-tools-test.txt") "w"))
(write-line "=== YS-Tools Test ===" __jtf)
(write-line (strcat "ACADVER: " (getvar "ACADVER")) __jtf)
(write-line (strcat "DWGPREFIX: " (getvar "DWGPREFIX")) __jtf)
(if (and (boundp '*YS-Tools-Path*) *YS-Tools-Path*)
  (progn
    (write-line (strcat "ROOT: " *YS-Tools-Path*) __jtf)
    (write-line (strcat "EXISTS config.lsp: " (if (findfile (strcat *YS-Tools-Path* "\\config.lsp")) "YES" "NO")) __jtf)
    (write-line (strcat "EXISTS utils.lsp: " (if (findfile (strcat *YS-Tools-Path* "\\utils.lsp")) "YES" "NO")) __jtf)
    (write-line (strcat "EXISTS color-tools.lsp: " (if (findfile (strcat *YS-Tools-Path* "\\modules\\color-tools.lsp")) "YES" "NO")) __jtf)
    (write-line "" __jtf)
    (write-line "--- Commands ---" __jtf)
    (foreach sym '(c:YS c:YSTOOLS c:Y c:RR c:ZUO c:LONG c:EXCEL c:HEI c:HE c:QW c:BIAN c:LAN c:XIN c:XY c:PAI c:ZDML c:HAO)
      (if (and (boundp sym) (functionp (eval sym)))
        (write-line (strcat "OK: " (vl-princ-to-string sym)) __jtf)
        (write-line (strcat "MISSING: " (vl-princ-to-string sym)) __jtf)
      )
    )
  )
  (write-line "FAIL: *YS-Tools-Path* is NOT SET!" __jtf)
)
(close __jtf)
(setq __jtf nil)
(princ)
