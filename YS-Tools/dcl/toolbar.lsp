;;; YS-Tools v1.5.0 toolbar controller
;;; Encoding: GBK/ANSI, CRLF

(if (and (boundp '*ys-toolbar-loaded*) *ys-toolbar-loaded*)
  (princ)
  (progn
    ;;; YS-Tools DCL toolbar controller
    ;;; Encoding: GBK/ANSI, CRLF

    (setq *YS-Tools-DCL-Path*
      (if (and (boundp '*YS-Tools-Path*) *YS-Tools-Path*)
        (strcat *YS-Tools-Path* "\\dcl\\toolbar.dcl")
        nil
      )
    )

    (setq *ys-aa-command-items*
      '(
        ("YSDL"      "[文字] YSDL - 导出选中文字到 CSV")
        ("QSTXT"     "[文字] QSTXT - 只保留文字选择")
        ("T"         "[文字] T - 拆分多行文字")
        ("HEI"       "[文字] HEI - 等距左对齐排列")
        ("HE"        "[文字] HE - 按顺序合并文字")
        ("QW"        "[文字] QW - 修改文字高度")
        ("WI"        "[文字] WI - 修改文字宽度")
        ("GTX"       "[文字] GTX - 分类提取文字")
        ("GTY"       "[文字] GTY - 表格化提取文字")
        ("KAI"       "[文字] KAI - 按空格拆分文字")
        ("DB"        "[文字] DB - 删除末尾字符")
        ("DF"        "[文字] DF - 删除开头字符")
        ("AB"        "[文字] AB - 末尾增加文字")
        ("AF"        "[文字] AF - 开头增加文字")
        ("ZI"        "[文字] ZI - 顿号连接并复制")
        ("C1"        "[文字] C1 - 递增复制文字")
        ("C2"        "[文字] C2 - 递减复制文字")
        ("DE"        "[文字] DE - 删除括号及内容")
        ("DE2"       "[文字] DE2 - 用括号内容替换数字")
        ("ZHONG"     "[对齐] ZHONG - 水平居中对齐")
        ("ZUO"       "[对齐] ZUO - 左对齐")
        ("HP"        "[对齐] HP - 水平等距排列")
        ("YOU"       "[对齐] YOU - 右对齐")
        ("SHANG"     "[对齐] SHANG - 上对齐")
        ("XIA"       "[对齐] XIA - 下对齐")
        ("ZHENG"     "[对齐] ZHENG - 对齐水平线中点")
        ("JZ"        "[对齐] JZ - 矩形对齐中心线")
        ("ZZ"        "[对齐] ZZ - 文字居中到周边线")
        ("JACC"      "[对齐] JACC - 文字居中到周边线")
        ("AW"        "[对齐] AW - 自动微移避让重叠")
        ("Y"         "[颜色] Y - 青色")
        ("RR"        "[颜色] RR - 红色")
        ("UU"        "[颜色] UU - 白色")
        ("GG"        "[颜色] GG - 绿色")
        ("HUI"       "[颜色] HUI - 颜色 8")
        ("YAN"       "[线段] YAN - 竖线统一延长")
        ("SYAN"      "[线段] SYAN - 向上延长")
        ("XYAN"      "[线段] XYAN - 向下延长")
        ("SJ"        "[线段] SJ - 上接短线")
        ("XJ"        "[线段] XJ - 下接短线")
        ("CE"        "[测量] CE - 测量点序列总长")
        ("GE"        "[表格] GE - 为单行文字画表格")
        ("FIVE"      "[缩放] FIVE - 将测得高度缩放为 5")
        ("BIAN"      "[电缆] BIAN - 生成电缆标注")
        ("LAN"       "[电缆] LAN - 线组联动复制")
        ("XIN"       "[电缆] XIN - 统计并标注芯数")
        ("XY"        "[电缆] XY - 芯数与文字提取")
        ("NU"        "[计算] NU - 文字数值减法")
        ("HAO"       "[图框] HAO - 批量填写页码")
        ("ZDML"      "[图框] ZDML - 自动生成目录")
        ("ZDMLDEBUG" "[图框] ZDMLDEBUG - 查看图框属性")
      )
    )

    (defun ys:run-command (cmd)
      (done_dialog 1)
      (vl-cmdf (strcat "_." cmd))
    )

    (defun ys:handle-button (key)
      (cond
        ((= key "btn_cont")   (ys:run-command "CONT"))
        ((= key "btn_txt")    (ys:run-command "TXT"))
        ((= key "btn_ysdl")   (ys:run-command "YSDL"))
        ((= key "btn_hei")    (ys:run-command "HEI"))
        ((= key "btn_qstxt")  (ys:run-command "QSTXT"))
        ((= key "btn_he")     (ys:run-command "HE"))
        ((= key "btn_qw")     (ys:run-command "QW"))
        ((= key "btn_wi")     (ys:run-command "WI"))
        ((= key "btn_gtx")    (ys:run-command "GTX"))
        ((= key "btn_gty")    (ys:run-command "GTY"))
        ((= key "btn_zhong")  (ys:run-command "ZHONG"))
        ((= key "btn_zuo")    (ys:run-command "ZUO"))
        ((= key "btn_you")    (ys:run-command "YOU"))
        ((= key "btn_shang")  (ys:run-command "SHANG"))
        ((= key "btn_xia")    (ys:run-command "XIA"))
        ((= key "btn_y")      (ys:run-command "Y"))
        ((= key "btn_rr")     (ys:run-command "RR"))
        ((= key "btn_uu")     (ys:run-command "UU"))
        ((= key "btn_gg")     (ys:run-command "GG"))
        ((= key "btn_syi")    (ys:run-command "SYI"))
        ((= key "btn_xyi")    (ys:run-command "XYI"))
        ((= key "btn_zyy")    (ys:run-command "ZYI"))
        ((= key "btn_yyi")    (ys:run-command "YYI"))
        ((= key "btn_yan")    (ys:run-command "YAN"))
        ((= key "btn_syan")   (ys:run-command "SYAN"))
        ((= key "btn_xyan")   (ys:run-command "XYAN"))
        ((= key "btn_xSUO")   (ys:run-command "XSUO"))
        ((= key "btn_sSUO")   (ys:run-command "SSUO"))
        ((= key "btn_sj")     (ys:run-command "SJ"))
        ((= key "btn_xj")     (ys:run-command "XJ"))
        ((= key "btn_long")   (ys:run-command "LONG"))
        ((= key "btn_excel")  (ys:run-command "EXCEL"))
        ((= key "btn_nu")     (ys:run-command "NU"))
        ((= key "btn_kuang")  (ys:run-command "KUANG"))
        ((= key "btn_bian")   (ys:run-command "BIAN"))
        ((= key "btn_lan")    (ys:run-command "LAN"))
        ((= key "btn_xin")    (ys:run-command "XIN"))
        ((= key "btn_xy")     (ys:run-command "XY"))
        ((= key "btn_pai")    (ys:run-command "PAI"))
        ((= key "btn_zdml")   (ys:run-command "ZDML"))
        ((= key "btn_hao")    (ys:run-command "HAO"))
        ((= key "btn_diag")   (ys:run-command "DIAGFRAME"))
        ((= key "btn_aa")     (done_dialog 2))
        ((= key "btn_aa_reload") (ys:run-command "YSRELOADAA"))
        ((= key "close_btn")  (done_dialog 0))
        (T nil)
      )
    )

    (defun ys:show-aa-toolbar (/ dcl_id dialog-result item selected)
      (cond
        ((null *YS-Tools-DCL-Path*)
         (princ "\n[YS-Tools] DCL path is not set."))
        ((not (findfile *YS-Tools-DCL-Path*))
         (princ (strcat "\n[YS-Tools] DCL file not found: " *YS-Tools-DCL-Path*)))
        (T
         (setq dcl_id (load_dialog *YS-Tools-DCL-Path*))
         (if (< dcl_id 0)
           (princ "\n[YS-Tools] Failed to load DCL dialog.")
           (progn
             (if (new_dialog "ys_aa_toolbar" dcl_id)
               (progn
                 (start_list "aa_command_list")
                 (foreach item *ys-aa-command-items*
                   (add_list (cadr item)))
                 (end_list)
                 (setq *ys-aa-selected-index* 0)
                 (set_tile "aa_command_list" "0")
                 (action_tile
                   "aa_command_list"
                   "(setq *ys-aa-selected-index* (atoi $value))")
                 (action_tile "aa_run_btn" "(done_dialog 1)")
                 (action_tile "aa_close_btn" "(done_dialog 0)")
                 (setq dialog-result (start_dialog))
               )
               (princ "\n[YS-Tools] Failed to create AA command dialog.")
             )
             (unload_dialog dcl_id)
             (if (= dialog-result 1)
               (progn
                 (setq selected
                   (nth *ys-aa-selected-index* *ys-aa-command-items*))
                 (if selected
                   (vl-cmdf (strcat "_." (car selected))))))
           )
         )
        )
      )
      (princ)
    )

    (defun ys:show-toolbar (/ dcl_id dialog-result)
      (cond
        ((null *YS-Tools-DCL-Path*)
         (princ "\n[YS-Tools] DCL path is not set."))
        ((not (findfile *YS-Tools-DCL-Path*))
         (princ (strcat "\n[YS-Tools] DCL file not found: " *YS-Tools-DCL-Path*)))
        (T
         (setq dcl_id (load_dialog *YS-Tools-DCL-Path*))
         (if (< dcl_id 0)
           (princ "\n[YS-Tools] Failed to load DCL dialog.")
           (progn
             (if (new_dialog "ys_tools_toolbar" dcl_id)
               (progn
                 (foreach k '("btn_cont" "btn_txt" "btn_ysdl" "btn_hei" "btn_qstxt" "btn_he" "btn_qw" "btn_wi" "btn_gtx" "btn_gty" "btn_zhong" "btn_zuo" "btn_you" "btn_shang" "btn_xia" "btn_y" "btn_rr" "btn_uu" "btn_gg" "btn_syi" "btn_xyi" "btn_zyy" "btn_yyi" "btn_yan" "btn_syan" "btn_xyan" "btn_xSUO" "btn_sSUO" "btn_sj" "btn_xj" "btn_long" "btn_excel" "btn_nu" "btn_kuang" "btn_bian" "btn_lan" "btn_xin" "btn_xy" "btn_pai" "btn_zdml" "btn_hao" "btn_diag" "btn_aa" "btn_aa_reload" "close_btn")
                   (action_tile k (strcat "(ys:handle-button \"" k "\")"))
                 )
                 (setq dialog-result (start_dialog))
               )
               (princ "\n[YS-Tools] Failed to create toolbar dialog.")
             )
             (unload_dialog dcl_id)
             (if (= dialog-result 2)
               (ys:show-aa-toolbar))
           )
         )
        )
      )
      (princ)
    )

    (defun C:YSTOOLS ()
      (vl-load-com)
      (ys:show-toolbar)
    )

    (princ "\n[YS-Tools] toolbar.lsp loaded.")
    (princ)
    (setq *ys-toolbar-loaded* T)
  )
)
(princ)
