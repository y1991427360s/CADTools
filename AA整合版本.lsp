;;; ====================================================================
;;; YS-Tools compatibility bundle v1.5.0
;;; AUTO-GENERATED by tools/build_bundle.py - DO NOT EDIT
;;; 此文件由模块源码自动生成，禁止手工修改。
;;; Encoding: GBK/ANSI, CRLF
;;; ====================================================================

;;; ----- BEGIN YS-Tools/config.lsp -----
;;; YS-Tools v1.5.0 configuration
;;; Encoding: GBK/ANSI, CRLF

;;; --- YSDL 命令相关参数 ---
(if (not (boundp '*YSDL_RowFuzz*)) (setq *YSDL_RowFuzz*      1.0)) ; 判断文字是否在同一行的 Y 坐标容差
(if (not (boundp '*YSDL_CsvFileName*)) (setq *YSDL_CsvFileName*  "output.csv")) ; 输出 CSV 文件名
(if (not (boundp '*YSDL_TextColor*)) (setq *YSDL_TextColor*    2)) ; 提取后文字颜色，ACI: 1 红, 2 黄, 3 绿, 4 青, 5 蓝, 6 品红, 7 白/黑

;;; --- CONT 命令相关参数 ---
(if (not (boundp '*CONT_TextStyle*)) (setq *CONT_TextStyle*       "宋体")) ; 目标文字样式名称
(if (not (boundp '*CONT_TextHeight*)) (setq *CONT_TextHeight*      4.0)) ; 目标文字高度
(if (not (boundp '*CONT_TextWidthFactor*)) (setq *CONT_TextWidthFactor* 0.8)) ; 目标文字宽度因子
(if (not (boundp '*CONT_LineSpacing*)) (setq *CONT_LineSpacing*     9.0)) ; 文字垂直间距

;;; --- EXCEL 命令相关参数 ---
(if (not (boundp '*EXCEL_LayerName*)) (setq *EXCEL_LayerName*  "表格")) ; 表格图层名称
(if (not (boundp '*EXCEL_LayerColor*)) (setq *EXCEL_LayerColor* 3)) ; 表格图层颜色

;;; --- 快速改色命令相关参数 ---
(if (not (boundp '*Y_TextColor*)) (setq *Y_TextColor*  4)) ; Y  命令: 青色
(if (not (boundp '*RR_TextColor*)) (setq *RR_TextColor* 1)) ; RR 命令: 红色
(if (not (boundp '*UU_TextColor*)) (setq *UU_TextColor* 7)) ; UU 命令: 白色/黑色
(if (not (boundp '*GG_TextColor*)) (setq *GG_TextColor* 3)) ; GG 命令: 绿色

;;; --- XY 命令相关参数 ---
(if (not (boundp '*xy-geom-tol*)) (setq *xy-geom-tol*        1e-4)) ; 几何容差
(if (not (boundp '*xy-ang-tol*)) (setq *xy-ang-tol*         (/ pi 180.0))) ; 角度容差 1 度
(if (not (boundp '*xy-ray-len*)) (setq *xy-ray-len*         20.0)) ; 搜索射线长度
(if (not (boundp '*xy-hit-half-width*)) (setq *xy-hit-half-width*  1.0)) ; 命中半宽
(if (not (boundp '*xy-out-offx*)) (setq *xy-out-offx*        10.0)) ; 输出文字 X 偏移
(if (not (boundp '*xy-out-offy*)) (setq *xy-out-offy*        1.0)) ; 输出文字 Y 偏移
(if (not (boundp '*xy-step-x*)) (setq *xy-step-x*          30.0)) ; 输出列间距
(if (not (boundp '*xy-warn-extend-len*)) (setq *xy-warn-extend-len* 200.0)) ; 异常标记延伸长度

;;; --- ZDML 自动目录参数 ---
(if (not (boundp '*TKTJ-COL-OFFSETS*)) (setq *TKTJ-COL-OFFSETS* '(0.0 7.5 57.5)))
(if (not (boundp '*TKTJ-ROW-GAP*)) (setq *TKTJ-ROW-GAP* 9.0))
(if (not (boundp '*TKTJ-TEXT-HEIGHT*)) (setq *TKTJ-TEXT-HEIGHT* 4.0))
(if (not (boundp '*TKTJ-TEXT-STYLE*)) (setq *TKTJ-TEXT-STYLE* "宋体"))
(if (not (boundp '*TKTJ-TEXT-FONTFILE*)) (setq *TKTJ-TEXT-FONTFILE* "simsun.ttc"))
(if (not (boundp '*TKTJ-TEXT-WIDTH-FACTOR*)) (setq *TKTJ-TEXT-WIDTH-FACTOR* 0.8))
(if (not (boundp '*TKTJ-OUTPUT-HEADER*)) (setq *TKTJ-OUTPUT-HEADER* T))
(if (not (boundp '*TKTJ-SORT-BY-POSITION*)) (setq *TKTJ-SORT-BY-POSITION* T))
(if (not (boundp '*TKTJ-ROW-SORT-TOL*)) (setq *TKTJ-ROW-SORT-TOL* 5.0))
(if (not (boundp '*TKTJ-SORT-BY-PAGE*)) (setq *TKTJ-SORT-BY-PAGE* nil))

;;; --- ZDML 图框属性标记 ---
(if (not (boundp '*TKTJ-SHEETNO-TAGS*)) (setq *TKTJ-SHEETNO-TAGS*   '("图号" "图纸编号" "DRAWINGNO" "DWGNO")))
(if (not (boundp '*TKTJ-SHEETNAME-TAGS*)) (setq *TKTJ-SHEETNAME-TAGS* '("图名" "图纸名称" "SHEETNAME" "DRAWINGNAME")))
(if (not (boundp '*TKTJ-PAGE-TAGS*)) (setq *TKTJ-PAGE-TAGS*      '("页码" "页号" "PAGE" "SHEET")))
(if (not (boundp '*TKTJ-ARCHIVE-TAGS*)) (setq *TKTJ-ARCHIVE-TAGS*   '("档案号" "工程号" "设计号" "DWGNO" "DRAWINGNO")))

(princ "\n[YS-Tools] config.lsp loaded.")
(princ)
;;; ----- END YS-Tools/config.lsp -----

;;; ----- BEGIN YS-Tools/utils.lsp -----
;;; YS-Tools v1.5.0 module
;;; Encoding: GBK/ANSI, CRLF

(if (and (boundp '*ys-module-utils-loaded*)
         *ys-module-utils-loaded*)
  (princ)
  (progn
    (vl-catch-all-apply 'vl-load-com '())

    (defun aa:try-get-bbox (vla_obj / min_pt max_pt result)
      (setq result
             (vl-catch-all-apply
               'vla-getboundingbox
               (list vla_obj 'min_pt 'max_pt)))
      (if (not (vl-catch-all-error-p result))
        (list (vlax-safearray->list min_pt)
              (vlax-safearray->list max_pt))
      )
    )

    (defun aa:safe-get-bbox (doc ename / vla_obj bbox)
      (if (and ename
               (setq vla_obj (vlax-ename->vla-object ename)))
        (progn
          (setq bbox (aa:try-get-bbox vla_obj))
          (if (null bbox)
            (progn
              (vl-catch-all-apply 'vla-update (list vla_obj))
              (entupd ename)
              (setq bbox (aa:try-get-bbox vla_obj))
            )
          )
          (if (and (null bbox) doc)
            (progn
              (vl-catch-all-apply 'vla-regen (list doc 0))
              (setq bbox (aa:try-get-bbox vla_obj))
            )
          )
          bbox
        )
      )
    )

    (defun aa:bbox-center-x (bbox)
      (/ (+ (car (car bbox))
            (car (cadr bbox)))
         2.0)
    )

    (defun aa:bbox-left-x (bbox)
      (car (car bbox))
    )

    (defun aa:bbox-right-x (bbox)
      (car (cadr bbox))
    )

    (defun aa:bbox-top-y (bbox)
      (cadr (cadr bbox))
    )

    (defun aa:bbox-bottom-y (bbox)
      (cadr (car bbox))
    )

    (defun aa:safe-move-entity (ename move_vec / vla_obj result)
      (if (and ename
               move_vec
               (setq vla_obj (vlax-ename->vla-object ename)))
        (progn
          (setq result
                 (vl-catch-all-apply
                   'vla-move
                   (list vla_obj
                         (vlax-3d-point '(0.0 0.0 0.0))
                         move_vec)))
          (if (not (vl-catch-all-error-p result))
            (progn
              (entupd ename)
              T
            )
            nil
          )
        )
      )
    )

    (defun aa:find-ref-by-left-bbox (doc ss / i ename bbox ref-ename ref-bbox)
      (setq i         0
            ref-ename nil
            ref-bbox  nil)
      (repeat (sslength ss)
        (setq ename (ssname ss i)
              bbox  (aa:safe-get-bbox doc ename))
        (if bbox
          (if (or (null ref-bbox)
                  (< (aa:bbox-left-x bbox)
                     (aa:bbox-left-x ref-bbox)))
            (setq ref-ename ename
                  ref-bbox  bbox))
        )
        (setq i (1+ i))
      )
      (if ref-bbox
        (list ref-ename ref-bbox))
    )

    (defun aa:find-ref-by-top-bbox (doc ss / i ename bbox ref-ename ref-bbox)
      (setq i         0
            ref-ename nil
            ref-bbox  nil)
      (repeat (sslength ss)
        (setq ename (ssname ss i)
              bbox  (aa:safe-get-bbox doc ename))
        (if bbox
          (if (or (null ref-bbox)
                  (> (aa:bbox-top-y bbox)
                     (aa:bbox-top-y ref-bbox)))
            (setq ref-ename ename
                  ref-bbox  bbox))
        )
        (setq i (1+ i))
      )
      (if ref-bbox
        (list ref-ename ref-bbox))
    )

    (defun aa:align-text-horizontal-by-bbox (doc ename base-x mode / bbox current-x delta-x)
      (if (setq bbox (aa:safe-get-bbox doc ename))
        (progn
          (setq current-x (if (= mode 3)
                            (aa:bbox-right-x bbox)
                            (aa:bbox-left-x bbox))
                delta-x   (- base-x current-x))
          (if (equal delta-x 0.0 1e-8)
            T
            (aa:safe-move-entity ename (vlax-3d-point (list delta-x 0.0 0.0)))))
      )
    )

    (defun aa:align-text-vertical-by-bbox (doc ename base-y mode / bbox current-y delta-y)
      (if (setq bbox (aa:safe-get-bbox doc ename))
        (progn
          (setq current-y (if (= mode 1)
                            (aa:bbox-top-y bbox)
                            (aa:bbox-bottom-y bbox))
                delta-y   (- base-y current-y))
          (if (equal delta-y 0.0 1e-8)
            T
            (aa:safe-move-entity ename (vlax-3d-point (list 0.0 delta-y 0.0)))))
      )
    )

    (setq *ys-module-utils-loaded* T)
    (princ "\n[YS-Tools] utils.lsp loaded.")
  )
)
(princ)
;;; ----- END YS-Tools/utils.lsp -----

;;; ----- BEGIN YS-Tools/modules/text-tools.lsp -----
;;; YS-Tools v1.5.0 module
;;; Encoding: GBK/ANSI, CRLF

(if (and (boundp '*ys-module-text_tools-loaded*)
         *ys-module-text_tools-loaded*)
  (princ)
  (progn
    (vl-catch-all-apply 'vl-load-com '())

    (defun aa:str-replace-all (old new str / start pos result old-len)
      (setq str     (if str str "")
            start   0
            result  ""
            old-len (strlen old))
      (if (= old-len 0)
        str
        (progn
          (while (setq pos (vl-string-search old str start))
            (setq result
                   (strcat
                     result
                     (if (> pos start)
                       (substr str (1+ start) (- pos start))
                       "")
                     new)
                  start (+ pos old-len))
          )
          (strcat result (substr str (1+ start)))
        )
      )
    )

    (defun aa:ysdl-get-raw-text (edata / etype raw pair)
      (setq etype (cdr (assoc 0 edata))
            raw   "")
      (cond
        ((= etype "MTEXT")
         (foreach pair edata
           (if (or (= (car pair) 3) (= (car pair) 1))
             (setq raw (strcat raw (cdr pair)))
           )
         )
        )
        (T
         (setq raw (cdr (assoc 1 edata)))
        )
      )
      (if raw raw "")
    )

    (defun aa:ysdl-strip-mtext-format (str / idx len out ch next semi stack)
      (setq str (if str str "")
            idx 1
            len (strlen str)
            out "")
      (while (<= idx len)
        (setq ch (substr str idx 1))
        (cond
          ((or (= ch "{") (= ch "}"))
           (setq idx (1+ idx)))
          ((/= ch "\\")
           (setq out (strcat out ch)
                 idx (1+ idx)))
          ((= idx len)
           (setq idx (1+ idx)))
          (T
           (setq next (substr str (1+ idx) 1))
           (cond
             ((or (= next "\\") (= next "{") (= next "}"))
              (setq out (strcat out next)
                    idx (+ idx 2)))
             ((or (= next "P") (= next "p") (= next "~"))
              (setq out (strcat out " ")
                    idx (+ idx 2)))
             ((or (= next "L") (= next "l")
                  (= next "O") (= next "o")
                  (= next "K") (= next "k")
                  (= next "X"))
              (setq idx (+ idx 2)))
             ((= next "S")
              (setq semi (vl-string-search ";" str (+ idx 1)))
              (if semi
                (progn
                  (setq stack (substr str (+ idx 2) (- semi idx 1)))
                  (setq stack (aa:str-replace-all "#" "/" stack))
                  (setq stack (aa:str-replace-all "^" "/" stack))
                  (setq out (strcat out stack)
                        idx (+ semi 2)))
                (setq idx (+ idx 2))
              )
             )
             ((or (= next "A") (= next "C") (= next "c")
                  (= next "F") (= next "f")
                  (= next "H") (= next "Q")
                  (= next "T") (= next "W"))
              (setq semi (vl-string-search ";" str (+ idx 1)))
              (if semi
                (setq idx (+ semi 2))
                (setq idx (+ idx 2))
              )
             )
             (T
              (setq out (strcat out next)
                    idx (+ idx 2)))
           )
          )
        )
      )
      out
    )

    (defun aa:ysdl-get-plain-text (edata / raw)
      (setq raw (aa:ysdl-get-raw-text edata))
      (if (= (cdr (assoc 0 edata)) "MTEXT")
        (setq raw (aa:ysdl-strip-mtext-format raw))
      )
      raw
    )

    (defun aa:ysdl-needs-text-formula (str / first)
      (and str
           (> (strlen str) 0)
           (setq first (substr str 1 1))
           (or (= first "=") (= first "+") (= first "-") (= first "@")))
    )

    (defun aa:ysdl-build-csv-field (cell / field)
      (setq field (if cell cell ""))
      (if (aa:ysdl-needs-text-formula field)
        (setq field (strcat (chr 9) field))
      )
      (setq field (aa:str-replace-all "\"" "\"\"" field))
      (strcat "\"" field "\"")
    )

    (defun c:YSDL (/ *error* ss i ent edata text-data-list sorted-data
                   csv-path f fuzz userprofile file-mode action-msg
                   ename targetColor text-string ins-point all-rows current-row
                   last-y item current-y line-str cell cell-safe)

      ;; 自定义错误处理函数
      (defun *error* (msg)
        (if (and f (= (type f) 'FILE))
          (close f)
        )
        (if (not (wcmatch (strcase msg) "*CANCEL*,*QUIT*"))
          (princ (strcat "\n发生错误: " msg))
        )
        (princ)
      )

      ;; 从全局配置获取容差值
      (setq fuzz *YSDL_RowFuzz*)

      ;; 1. 提示用户选择文字对象
      (princ "\n请选择要导出并改变颜色的文字对象: ")
      (setq ss (ssget '((0 . "TEXT,MTEXT"))))

      (if ss
        (progn
          ;; 2. 提取所选文字的内容和插入点坐标
          (setq text-data-list '()
                i 0)
          (repeat (sslength ss)
            (setq ent (ssname ss i))
            (setq edata (entget ent))
            (setq text-string (aa:ysdl-get-plain-text edata))
            (setq ins-point (cdr (assoc 10 edata)))
            (setq text-data-list (cons (list text-string ins-point) text-data-list))
            (setq i (1+ i))
          )

          ;; 3. 按坐标排序 (从上到下，从左到右)
          (setq sorted-data
                 (vl-sort text-data-list
                          '(lambda (item1 item2)
                             (setq y1 (cadr (cadr item1)))
                             (setq y2 (cadr (cadr item2)))
                             (if (> y1 (+ y2 fuzz))
                               T
                               (if (< y1 (- y2 fuzz))
                                 nil
                                 (< (car (cadr item1)) (car (cadr item2)))
                               )
                             )
                           )
                 )
          )

          ;; 4. 将排序后的数据按行分组
          (setq all-rows '())
          (if sorted-data
            (progn
              (setq current-row (list (car (car sorted-data))))
              (setq last-y (cadr (cadr (car sorted-data))))
              (foreach item (cdr sorted-data)
                (setq current-y (cadr (cadr item)))
                (if (<= (abs (- current-y last-y)) fuzz)
                  (setq current-row (append current-row (list (car item))))
                  (progn
                    (setq all-rows (append all-rows (list current-row)))
                    (setq current-row (list (car item)))
                  )
                )
                (setq last-y current-y)
              )
              (setq all-rows (append all-rows (list current-row)))
            )
          )

          ;; 5. 自动定位桌面路径并写入或追加CSV文件
          (setq userprofile (getenv "USERPROFILE"))
          (if (and userprofile (/= userprofile ""))
            (progn
              (setq csv-path (strcat userprofile "\\Desktop\\" *YSDL_CsvFileName*))
              (if (findfile csv-path)
                (progn (setq file-mode "a") (setq action-msg "数据已成功追加到桌面文件:\n"))
                (progn (setq file-mode "w") (setq action-msg "已在桌面成功创建文件:\n"))
              )

              (setq f (open csv-path file-mode))
              (foreach row all-rows
                (setq line-str "")
                (foreach cell row
                    (setq cell-safe (aa:ysdl-build-csv-field cell))
                    (setq line-str (strcat line-str cell-safe ","))
                )
                (setq line-str (substr line-str 1 (1- (strlen line-str))))
                (write-line line-str f)
              )
              (close f)

              ;; 修改已导出文字的颜色
              (setq targetColor *YSDL_TextColor*)
              (setq i 0)
              (repeat (sslength ss)
                (setq ename (ssname ss i))
                (vla-put-Color (vlax-ename->vla-object ename) targetColor)
                (setq i (1+ i))
              )

              (alert (strcat action-msg csv-path "\n\n并且所有选中的文字颜色已更改。"))
            )
            (alert "错误: 无法自动获取您的桌面路径!")
          )
        )
        (princ "\n未选择任何文字对象。")
      )
      (princ)
    )

    (defun C:CONT ( / ss i en edata ent-list sorted-list ref-pt target-x current-y new-pt etype orig-z top-en top-edata pt)
      (command "_.UNDO" "_Begin")
      (setq ss (ssget "_P" '((0 . "TEXT,MTEXT"))))

      (if (not ss)
        (progn
          (princ "\n未预先选择对象，请选择要修改和对齐的文字: ")
          (setq ss (ssget '((0 . "TEXT,MTEXT"))))
        )
      )

      (if ss
        (progn
          (if (not (tblsearch "STYLE" *CONT_TextStyle*))
            (alert (strcat "错误：\n\n当前图纸中不存在名为“" *CONT_TextStyle* "”的文字样式。\n请先创建该样式后再运行本插件。"))
            (progn
              (setq i 0 ent-list '())
              (repeat (sslength ss)
                (setq en (ssname ss i))
                (setq edata (entget en))
                (setq pt (cdr (assoc 10 edata)))
                (setq ent-list (cons (list (cadr pt) en) ent-list))
                (setq i (1+ i))
              )

              (setq sorted-list (vl-sort ent-list '(lambda (a b) (> (car a) (car b)))))

              (setq top-en (cadr (car sorted-list)))
              (setq top-edata (entget top-en))
              (setq ref-pt (cdr (assoc 10 top-edata)))

              (setq target-x (car ref-pt))
              (setq current-y (cadr ref-pt))

              (foreach item sorted-list
                (setq en (cadr item))
                (setq edata (entget en))
                (setq etype (cdr (assoc 0 edata)))
                (setq orig-z (caddr (cdr (assoc 10 edata))))

                (setq new-pt (list target-x current-y orig-z))

                (setq edata (subst (cons 7 *CONT_TextStyle*) (assoc 7 edata) edata))
                (setq edata (subst (cons 40 *CONT_TextHeight*) (assoc 40 edata) edata))
                (setq edata (subst (cons 10 new-pt) (assoc 10 edata) edata))

                (if (= etype "TEXT")
                  (progn
                    (setq edata (subst (cons 41 *CONT_TextWidthFactor*) (assoc 41 edata) edata))
                    (setq edata (subst (cons 72 0) (assoc 72 edata) edata))
                    (setq edata (subst (cons 73 0) (assoc 73 edata) edata))
                  )
                  (setq edata (subst (cons 71 7) (assoc 71 edata) edata))
                )

                (entmod edata)
                (setq current-y (- current-y *CONT_LineSpacing*))
              )
              (princ (strcat "\n已成功处理 " (itoa (length sorted-list)) " 个文字对象。"))
            )
          )
        )
        (princ "\n未选择任何文字对象。")
      )
      (command "_.UNDO" "_End")
      (princ)
    )

    (defun c:qstxt (/ ss i ent txt)
      (setq ss (ssget))
      (if ss
        (progn
          (setq txt (ssadd))
          (setq i 0)
          (while (< i (sslength ss))
            (setq ent (ssname ss i))
            (if (wcmatch (cdr (assoc 0 (entget ent))) "*TEXT")
              (ssadd ent txt)
            )
            (setq i (1+ i))
          )

          (if (> (sslength txt) 0)
            (progn
              (sssetfirst nil txt)
              (princ (strcat "\n已选择 " (itoa (sslength txt)) " 个文字对象"))
            )
            (princ "\n所选对象中没有找到文字对象")
          )
        )
        (princ "\n未选择任何对象")
      )
      (princ)
    )

        (defun txt:set-dxf (code value data / item)
      (if (setq item (assoc code data))
        (subst (cons code value) item data)
        (append data (list (cons code value)))
      )
    )

    (defun txt:modify-text (ename / edata)
      (if (and ename (= "TEXT" (cdr (assoc 0 (setq edata (entget ename))))))
        (progn
          (setq edata (txt:set-dxf 7 "HZ" edata))
          (setq edata (txt:set-dxf 40 3.0 edata))
          (setq edata (txt:set-dxf 41 0.7 edata))
          (if (entmod edata) 1 0)
        )
        0
      )
    )

    (defun txt:modify-new-texts (before after / cur count)
      (setq count 0)
      (if (and after (not (eq before after)))
        (progn
          (setq cur (if before (entnext before) (entnext)))
          (while cur
            (if (= "TEXT" (cdr (assoc 0 (entget cur))))
              (setq count (+ count (txt:modify-text cur)))
            )
            (if (eq cur after)
              (setq cur nil)
              (setq cur (entnext cur))
            )
          )
        )
      )
      count
    )

    (defun txt:process-selection (sel / *error* oldcmdecho total i ename etype mtss mtlist before after count)
      (defun *error* (msg)
        (if oldcmdecho
          (setvar "CMDECHO" oldcmdecho)
        )
        (if (and msg (/= msg "Function cancelled") (/= msg "quit / exit abort"))
          (princ (strcat "\nError: " msg))
        )
        (princ)
      )

      (setq oldcmdecho (getvar "CMDECHO"))
      (setvar "CMDECHO" 0)
      (setq total  (sslength sel)
            mtss   (ssadd)
            mtlist '()
            count  0
            i      0)

      ;; Modify TEXT immediately instead of building another large selection set.
      (while (< i total)
        (setq ename (ssname sel i)
              etype (cdr (assoc 0 (entget ename))))
        (cond
          ((= etype "TEXT")
           (setq count (+ count (txt:modify-text ename))))
          ((= etype "MTEXT")
           (ssadd ename mtss)
           (setq mtlist (cons ename mtlist)))
        )
        (setq i (1+ i))
      )

      ;; Explode all MTEXT objects in one native command invocation.
      (if (> (sslength mtss) 0)
        (progn
          (setq before (entlast))
          (command "_.explode" mtss "")

          ;; Retry only objects left behind by CAD versions that do not accept a
          ;; multi-object selection set from AutoLISP EXPLODE.
          (foreach ename mtlist
            (if (= "MTEXT" (cdr (assoc 0 (entget ename))))
              (command "_.explode" ename)
            )
          )

          ;; Process the new database range directly; do not copy it into a list
          ;; or reselect every result, both of which are costly in ZWCAD.
          (setq after (entlast)
                count (+ count (txt:modify-new-texts before after)))
        )
      )

      (redraw)
      (setvar "CMDECHO" oldcmdecho)
      (princ (strcat "\nProcessed text count: " (itoa count)))
      count
    )

    (defun txt:run (/ sel)
      (if (null (tblsearch "STYLE" "HZ"))
        (princ "\nText style HZ was not found.")
        (progn
          (setq sel (ssget '((0 . "TEXT,MTEXT"))))
          (if sel
            (txt:process-selection sel)
            (princ "\nNo objects were selected.")
          )
        )
      )
      (princ)
    )

    (defun c:TXT ()
      (txt:run)
    )

    (defun c:T ()
      (txt:run)
    )

    (defun c:HEI (/ a ss ent ent_data text_type insertion_point x y text_content
                  text_list sorted_text_list base_x max_y current_y count modified_data)
      (vl-load-com) ; 加载 Visual LISP 扩展功能
      (setq a (getdist "\n请输入上下间距 <5>: "))
      (if (not a)
        (setq a 5)
      )

      (princ "\n选择要对齐的文字对象: ")
      (setq ss (ssget '((0 . "TEXT,MTEXT"))))

      (if (not ss)
        (progn (princ "\n未选择任何文字对象。") (exit))
      )

      (setq text_list '() count 0)
      (repeat (sslength ss)
        (setq ent (ssname ss count) ent_data (entget ent) text_type (cdr (assoc 0 ent_data)) modified_data ent_data)

        (cond
          ((= text_type "TEXT")
            ;; 修改水平对齐 (72) 为 0 (左对齐)
            (if (assoc 72 modified_data)
                (setq modified_data (subst (cons 72 0) (assoc 72 modified_data) modified_data))
                (setq modified_data (append modified_data (list (cons 72 0))))
            )
            ;; 修改垂直对齐 (73) 为 0 (基线对齐)
            (if (assoc 73 modified_data)
                (setq modified_data (subst (cons 73 0) (assoc 73 modified_data) modified_data))
                (setq modified_data (append modified_data (list (cons 73 0))))
            )
            ;; 移除组码 11 (对齐点)，左对齐不需要此点
            (if (assoc 11 modified_data) (setq modified_data (vl-remove (assoc 11 modified_data) modified_data)))
          )
          ((= text_type "MTEXT")
            ;; 修改对齐点 (71) 为 1 (左上角)
            (if (assoc 71 modified_data)
                (setq modified_data (subst (cons 71 1) (assoc 71 modified_data) modified_data))
                (setq modified_data (append modified_data (list (cons 71 1))))
            )
          )
        )

        ;; 先更新实体对齐方式，这样文字的插入点会自动更新到左侧位置
        (entmod modified_data)

        ;; 重新获取数据以读取更新后的坐标
        (setq ent_data (entget ent)
              insertion_point (cdr (assoc 10 ent_data))
              x (car insertion_point)
              y (cadr insertion_point)
              text_content (cdr (assoc 1 ent_data)) ; 注意：MTEXT 内容可能很长，但这不影响排序逻辑
        )

        ;; 保存数据用于排序：Y坐标 X坐标 内容 实体名
        (setq text_list (cons (list y x text_content ent) text_list))
        (setq count (1+ count))
      )

      ;; 排序逻辑：按 Y 坐标从大到小排序 (从上到下)
      (setq sorted_text_list (vl-sort text_list '(lambda (a b) (> (car a) (car b)))))

      ;; 计算基准点：X取所有文字中最小的X值(最左边)，起始Y取最高的Y值
      (setq base_x (apply 'min (mapcar 'cadr sorted_text_list))
            max_y (apply 'max (mapcar 'car sorted_text_list)))

      (setq current_y max_y count 0)

      (foreach text_info sorted_text_list
        (setq ent (last text_info) ent_data (entget ent))
        ;; 保持原有的 Z 坐标
        (setq new_insertion_point (list base_x current_y (caddr (cdr (assoc 10 ent_data))))
              ent_data (subst (cons 10 new_insertion_point) (assoc 10 ent_data) ent_data))
        (entmod ent_data)
        (setq current_y (- current_y a))
        (setq count (1+ count))
      )

      (princ (strcat "\n成功对齐并排列了 " (itoa count) " 个文字对象，并已统一设置为左对齐。"))
      (princ)
    )

    (defun c:HE (/ ss lst i ent ent-data pt txt ht sorted-lst master-ent master-data new-str)
      (vl-load-com) ;; 加载 VL 扩展函数

      (princ "\n请选择需要合并的文字(按照从上到下，从左到右的逻辑合并):")

      ;; 1. 选择文字对象 (过滤 Text 和 MText)
      (if (setq ss (ssget '((0 . "TEXT,MTEXT"))))
        (progn
          (setq lst '())
          (setq i 0)

          ;; 2. 遍历选择集，提取实体名、坐标、高度和内容
          (repeat (sslength ss)
            (setq ent (ssname ss i))
            (setq ent-data (entget ent))
            (setq pt (cdr (assoc 10 ent-data))) ;; 插入点
            (setq txt (cdr (assoc 1 ent-data))) ;; 文字内容
            (setq ht (cdr (assoc 40 ent-data))) ;; 文字高度 (用于判断容差)

            ;; 将数据存入列表: (实体名 插入点 文字内容 文字高度)
            (setq lst (cons (list ent pt txt ht) lst))
            (setq i (1+ i))
          )

          ;; 3. 排序算法 (修正版：去除 let，使用标准 AutoLISP)
          (setq sorted-lst
            (vl-sort lst
              (function (lambda (e1 e2 / p1 p2 h y1 y2 x1 x2)
                ;; 提取变量
                (setq p1 (cadr e1))
                (setq p2 (cadr e2))
                (setq h (cadddr e1)) ;; 使用第一个对象的文字高度做参考
                (setq y1 (cadr p1))
                (setq y2 (cadr p2))
                (setq x1 (car p1))
                (setq x2 (car p2))

                ;; 判断逻辑
                (if (> (abs (- y1 y2)) (* h 0.5))
                  (> y1 y2) ;; Y轴差值大：按Y从大到小(上到下)
                  (< x1 x2) ;; Y轴差值小(同一行)：按X从小到大(左到右)
                )
              ))
            )
          )

          ;; 4. 合并文字
          (setq master-ent (car (car sorted-lst))) ;; 获取排序后的第一个实体作为主实体
          (setq new-str "")

          ;; 遍历排序后的列表，拼接字符串
          (foreach item sorted-lst
            (setq new-str (strcat new-str (caddr item)))
          )

          ;; 5. 更新主实体并删除其他实体
          ;; 更新主实体内容
          (setq master-data (entget master-ent))
          (setq master-data (subst (cons 1 new-str) (assoc 1 master-data) master-data))
          (entmod master-data)
          (entupd master-ent)

          ;; 删除其余实体
          (foreach item (cdr sorted-lst)
            (entdel (car item))
          )

          (princ (strcat "\n成功合并 " (itoa (length sorted-lst)) " 个文字对象。结果: " new-str))
        )
        (princ "\n未选中任何文字对象。")
      )
      (princ)
    )

    (defun c:QW (/ a ss i ent data)
      ;; 1. 提示用户输入高度值并存储在变量 a 中
      (setq a (getdist "\n请输入新的文字高度: "))

      ;; 2. 检查高度值是否有效
      (if (and a (> a 0))
        (progn
          ;; 3. 提示用户选择对象，并过滤出单行文字(TEXT)和多行文字(MTEXT)
          (princ "\n请选择需要修改高度的文字内容...")
          (setq ss (ssget '((0 . "TEXT,MTEXT"))))

          ;; 4. 检查是否选中了内容
          (if ss
            (progn
              (setq i 0)
              ;; 5. 遍历选择集
              (repeat (sslength ss)
                (setq ent (ssname ss i))
                (setq data (entget ent))

                ;; 6. 使用 subst 和 entmod 修改 DXF 组码 40 (高度)
                ;; assoc 40 获取当前高度，cons 40 a 构造新的高度项
                (setq data (subst (cons 40 a) (assoc 40 data) data))
                (entmod data)

                (setq i (1+ i))
              )
              (princ (strcat "\n操作成功！已将 " (itoa i) " 个文字的高度修改为: " (rtos a)))
            )
            (princ "\n未选中任何文字对象。")
          )
        )
        (princ "\n错误：请输入有效的高度数值。")
      )
      ;; 静默退出
      (princ)
    )

    (defun c:wi (/ a ss i ename elist old_width)
      ;; 1. 提示用户输入文字宽度比例
      (setq a (getreal "\n请输入新的文字宽度比例 (例如 0.8 或 1.0): "))

      ;; 2. 检查输入是否有效
      (if (and a (> a 0))
        (progn
          ;; 3. 提示选择对象（过滤只选择 TEXT 和 MTEXT）
          (princ "\n请选择要修改的文字对象: ")
          (setq ss (ssget '((0 . "TEXT,MTEXT"))))

          (if ss
            (progn
              (setq i 0)
              ;; 4. 遍历选择集
              (repeat (sslength ss)
                (setq ename (ssname ss i))
                (setq elist (entget ename))

                ;; 对于普通文字 (TEXT)，41号组码是宽度比例
                ;; 对于多行文字 (MTEXT)，41号组码是参照矩形宽度
                ;; 这里统一处理 41 号组码
                (if (assoc 41 elist)
                  (setq elist (subst (cons 41 a) (assoc 41 elist) elist))
                  (setq elist (append elist (list (cons 41 a))))
                )

                ;; 更新实体数据
                (entmod elist)
                (setq i (1+ i))
              )
              (princ (strcat "\n成功修改了 " (itoa (sslength ss)) " 个文字的宽度比例。"))
            )
            (princ "\n未选中任何有效的文字对象。")
          )
        )
        (princ "\n无效的宽度数值，请输入大于0的数字。")
      )
      (princ)
    )

    (defun aa:gtx-find-last-char (char str / len pos)
      (setq len (strlen str)
            pos nil)
      (while (and (> len 0) (not pos))
        (if (= (substr str len 1) char)
          (setq pos len)
          (setq len (1- len))
        )
      )
      pos
    )

    (defun aa:gtx-parse-suffix (suffix / i char num-str alpha-str)
      (setq i 1
            num-str ""
            alpha-str "")
      (while (<= i (strlen suffix))
        (setq char (substr suffix i 1))
        (if (wcmatch char "#")
          (setq num-str (strcat num-str char))
          (setq alpha-str (strcat alpha-str char))
        )
        (setq i (1+ i))
      )
      (list (atoi num-str) alpha-str)
    )

    (defun aa:gtx-create-text-entity (pt content h sty)
      (entmake
        (list
          '(0 . "TEXT")
          (cons 10 pt)
          (cons 40 h)
          (cons 1 content)
          (cons 7 sty)
          '(41 . 0.7)
          '(62 . 7)))
    )

    (defun aa:gtx-first-text-from-ss (ss / i en)
      (setq i 0
            en nil)
      (while (and ss (< i (sslength ss)) (not en))
        (if (eq "TEXT" (cdr (assoc 0 (entget (ssname ss i)))))
          (setq en (ssname ss i))
        )
        (setq i (1+ i))
      )
      en
    )

    (defun aa:gtx-select-prefix-text (/ prefix-ss prefix-ent)
      (setq prefix-ent nil)
      (while (not prefix-ent)
        (sssetfirst nil nil)
        (prompt "\n[GTX] Select TEXT to add before each group (window selection supported): ")
        (setq prefix-ss (ssget '((0 . "TEXT"))))
        (setq prefix-ent (aa:gtx-first-text-from-ss prefix-ss))
        (if (not prefix-ent)
          (prompt "\n[GTX] No TEXT selected. Select or window-select one TEXT; press Esc to cancel.")
        )
      )
      prefix-ent
    )

    (defun c:GTX (/ *error* ss i ent ent-data text-data text-string insertion-point
                   lines current-item current-y found line categorized-groups
                   left-text temp-text last-hyphen-pos category group-texts found-category
                   pt start-x current-x col-width line-height text-height text-style
                   category-group groups-in-category sorted-groups group text-item
                   split-groups current-group last-item-x current-item-x
                   prefix-text-ent prefix-text-str)

      (vl-load-com)
      (setq text-style (if (tblsearch "STYLE" "HZ")
                         "HZ"
                         (getvar "TEXTSTYLE")))

      (defun *error* (msg)
        (if (not (member msg '("Function cancelled" "quit / exit abort")))
          (princ (strcat "\n[GTX] Error: " msg))
        )
        (sssetfirst nil nil)
        (princ)
      )

      (setq ss (ssget "_I" '((0 . "TEXT"))))
      (if (not ss)
        (progn
          (prompt "\n[GTX] Select text to classify: ")
          (setq ss (ssget '((0 . "TEXT"))))
        )
      )

      (if ss
        (progn
          (setq prefix-text-ent (aa:gtx-select-prefix-text))
          (setq prefix-text-str (cdr (assoc 1 (entget prefix-text-ent))))

          (if prefix-text-str
            (progn
              (setq text-data '()
                    i         0)
              (repeat (sslength ss)
                (setq ent             (ssname ss i)
                      ent-data        (entget ent)
                      text-string     (cdr (assoc 1 ent-data))
                      insertion-point (cdr (assoc 10 ent-data))
                      text-data       (cons (list text-string insertion-point) text-data)
                      i               (1+ i))
              )

              (setq lines '())
              (foreach current-item text-data
                (setq current-y (cadr (cadr current-item))
                      found     nil)
                (setq lines
                  (mapcar
                    '(lambda (line)
                       (if (and (not found)
                                (< (abs (- current-y (cadr (cadr (car line))))) 1.0))
                         (progn
                           (setq found T)
                           (cons current-item line))
                         line))
                    lines))
                (if (not found)
                  (setq lines (cons (list current-item) lines)))
              )

              (setq lines
                (mapcar
                  '(lambda (line)
                     (vl-sort line '(lambda (a b) (< (car (cadr a)) (car (cadr b))))))
                  lines))

              (setq split-groups '())
              (foreach line lines
                (if line
                  (progn
                    (setq current-group (list (car line))
                          last-item-x   (car (cadr (car line))))
                    (foreach item (cdr line)
                      (setq current-item-x (car (cadr item)))
                      (if (> (- current-item-x last-item-x) 200.0)
                        (progn
                          (setq split-groups (cons current-group split-groups))
                          (setq current-group (list item)))
                        (setq current-group (append current-group (list item)))
                      )
                      (setq last-item-x current-item-x)
                    )
                    (setq split-groups (cons current-group split-groups))
                  )
                )
              )
              (setq lines (reverse split-groups))

              (setq categorized-groups '())
              (foreach line lines
                (if (>= (length line) 1)
                  (progn
                    (setq left-text (caar line)
                          temp-text left-text)
                    (if (wcmatch temp-text "并入*")
                      (setq temp-text (vl-string-subst "" "并入" temp-text))
                    )
                    (setq last-hyphen-pos (aa:gtx-find-last-char "-" temp-text))
                    (if last-hyphen-pos
                      (setq category (substr temp-text 1 last-hyphen-pos))
                      (setq category temp-text)
                    )
                    (setq group-texts    (mapcar 'car line)
                          found-category (assoc category categorized-groups))
                    (if found-category
                      (setq categorized-groups
                        (subst
                          (list category (cons group-texts (cadr found-category)))
                          found-category
                          categorized-groups))
                      (setq categorized-groups
                        (cons (list category (list group-texts)) categorized-groups))
                    )
                  )
                )
              )

              (setq pt (getpoint "\n[GTX] Specify insertion point for summary: "))
              (if pt
                (progn
                  (setq text-height 3.0
                        start-x     (car pt)
                        current-y   (cadr pt)
                        col-width   50.0
                        line-height (* 1.4 text-height))

                  (setq categorized-groups
                    (vl-sort categorized-groups '(lambda (a b) (< (car a) (car b)))))

                  (foreach category-group categorized-groups
                    (setq groups-in-category (cadr category-group))

                    (setq sorted-groups
                      (vl-sort
                        groups-in-category
                        '(lambda (itemA itemB / keyA keyB posA posB suffixA suffixB parsedA parsedB numA alphaA numB alphaB)
                           (setq keyA (car itemA)
                                 keyB (car itemB)
                                 posA (aa:gtx-find-last-char "-" keyA)
                                 posB (aa:gtx-find-last-char "-" keyB))
                           (if (and posA posB)
                             (progn
                               (setq suffixA (substr keyA (1+ posA))
                                     suffixB (substr keyB (1+ posB))
                                     parsedA (aa:gtx-parse-suffix suffixA)
                                     parsedB (aa:gtx-parse-suffix suffixB)
                                     numA    (car parsedA)
                                     alphaA  (cadr parsedA)
                                     numB    (car parsedB)
                                     alphaB  (cadr parsedB))
                               (if (= numA numB)
                                 (< alphaA alphaB)
                                 (< numA numB)))
                             (< keyA keyB))))
                    )

                    (foreach group sorted-groups
                      (setq current-x start-x)
                      (aa:gtx-create-text-entity (list current-x current-y 0.0) prefix-text-str text-height text-style)
                      (setq current-x (+ current-x col-width))
                      (foreach text-item group
                        (aa:gtx-create-text-entity (list current-x current-y 0.0) text-item text-height text-style)
                        (setq current-x (+ current-x col-width))
                      )
                      (setq current-y (- current-y line-height))
                    )
                    (setq current-y (- current-y (* 0.5 line-height)))
                  )
                  (princ "\n[GTX] Text classification completed.")
                )
                (princ "\n[GTX] Operation cancelled.")
              )
            )
            (princ "\n[GTX] No valid prefix TEXT selected.")
          )
        )
        (princ "\n[GTX] No text selected.")
      )
      (sssetfirst nil nil)
      (princ)
    )

    (defun aa:gty-pad-left (txt size / result)
      (setq result txt)
      (while (< (strlen result) size)
        (setq result (strcat "0" result))
      )
      result
    )

    (defun aa:gty-normalize-key (txt / src i char num-buf result)
      (setq src     (strcase (vl-string-trim " " (if txt txt "")))
            i       1
            num-buf ""
            result  "")
      (while (<= i (strlen src))
        (setq char (substr src i 1))
        (if (wcmatch char "#")
          (setq num-buf (strcat num-buf char))
          (progn
            (if (> (strlen num-buf) 0)
              (progn
                (setq result  (strcat result (aa:gty-pad-left num-buf 8))
                      num-buf ""))
            )
            (setq result (strcat result char))
          )
        )
        (setq i (1+ i))
      )
      (if (> (strlen num-buf) 0)
        (setq result (strcat result (aa:gty-pad-left num-buf 8)))
      )
      result
    )

    (defun aa:gty-get-item-ename (item) (nth 0 item))

    (defun aa:gty-get-item-text  (item) (nth 1 item))

    (defun aa:gty-get-item-pt    (item) (nth 2 item))

    (defun aa:gty-get-item-x     (item) (car (aa:gty-get-item-pt item)))

    (defun aa:gty-get-item-y     (item) (cadr (aa:gty-get-item-pt item)))

    (defun aa:gty-get-item-z     (item / pt)
      (setq pt (aa:gty-get-item-pt item))
      (if (caddr pt) (caddr pt) 0.0)
    )

    (defun aa:gty-get-item-width (item) (nth 3 item))

    (defun aa:gty-get-item-height (item) (nth 4 item))

    (defun aa:gty-build-sort-key (row idx / key)
      (if (>= (length row) 4)
        (setq key (aa:gty-normalize-key (aa:gty-get-item-text (nth 1 row))))
        (setq key "")
      )
      (strcat
        (if (> (strlen key) 0) "0|" "1|")
        key
        "|"
        (aa:gty-pad-left (itoa idx) 6))
    )

    (defun aa:gty-get-text-width (edata / box p1 p2 h txt)
      (setq h   (cond ((cdr (assoc 40 edata))) (3.0))
            txt (cdr (assoc 1 edata))
            box (textbox edata))
      (if (and box (= (length box) 2))
        (progn
          (setq p1 (car box)
                p2 (cadr box))
          (max (- (car p2) (car p1)) h))
        (max (* (strlen txt) h 0.7) h))
    )

    (defun aa:gty-update-nth (idx val lst / n result)
      (setq n 0
            result '())
      (foreach itm lst
        (setq result (cons (if (= n idx) val itm) result)
              n      (1+ n))
      )
      (reverse result)
    )

    (defun aa:gty-move-entity (ename from-pt to-pt / obj)
      (setq obj (vlax-ename->vla-object ename))
      (vla-move obj (vlax-3d-point from-pt) (vlax-3d-point to-pt))
    )

    (defun c:GTY (/ *error* ss i ent ent-data text-string insertion-point text-height text-width
                   text-data total-height avg-height row-tol split-gap col-gap line-height
                   rows current-item current-y found split-rows current-row last-item-x current-item-x
                   anchor-x anchor-y col-widths col-index row row-index sort-keys row-map token sorted-rows
                   doc undo-started)

      (vl-load-com)
      (setq doc          (vla-get-ActiveDocument (vlax-get-acad-object))
            undo-started nil)

      (defun *error* (msg)
        (if undo-started
          (vla-EndUndoMark doc)
        )
        (if (not (member msg '("Function cancelled" "quit / exit abort")))
          (princ (strcat "\n[GTY] Error: " msg))
        )
        (sssetfirst nil nil)
        (princ)
      )

      (setq ss (ssget "_I" '((0 . "TEXT"))))
      (if (not ss)
        (progn
          (prompt "\n[GTY] Select cable text to organize: ")
          (setq ss (ssget '((0 . "TEXT"))))
        )
      )

      (if ss
        (progn
          (vla-StartUndoMark doc)
          (setq undo-started T
                text-data     '()
                total-height  0.0
                i             0)

          (repeat (sslength ss)
            (setq ent             (ssname ss i)
                  ent-data        (entget ent)
                  text-string     (cdr (assoc 1 ent-data))
                  insertion-point (cdr (assoc 10 ent-data))
                  text-height     (cond ((cdr (assoc 40 ent-data))) (3.0))
                  text-width      (aa:gty-get-text-width ent-data)
                  text-data       (cons (list ent text-string insertion-point text-width text-height) text-data)
                  total-height    (+ total-height text-height)
                  i               (1+ i))
          )
          (setq text-data (reverse text-data))

          (setq avg-height  (/ total-height (max 1 (length text-data)))
                row-tol     (max 1.0 (* avg-height 0.6))
                split-gap   200.0
                col-gap     (max 10.0 (* avg-height 2.0))
                line-height (max (* avg-height 1.6) (+ avg-height 1.0)))

          (setq rows '())
          (foreach current-item text-data
            (setq current-y (aa:gty-get-item-y current-item)
                  found     nil)
            (setq rows
              (mapcar
                '(lambda (line)
                   (if (and (not found)
                            (<= (abs (- current-y (aa:gty-get-item-y (car line)))) row-tol))
                     (progn
                       (setq found T)
                       (cons current-item line))
                     line))
                rows))
            (if (not found)
              (setq rows (cons (list current-item) rows))
            )
          )

          (setq rows
            (mapcar
              '(lambda (line)
                 (vl-sort line '(lambda (a b) (< (aa:gty-get-item-x a) (aa:gty-get-item-x b)))))
              rows))

          (setq split-rows '())
          (foreach row rows
            (if row
              (progn
                (setq current-row (list (car row))
                      last-item-x (aa:gty-get-item-x (car row)))
                (foreach current-item (cdr row)
                  (setq current-item-x (aa:gty-get-item-x current-item))
                  (if (> (- current-item-x last-item-x) split-gap)
                    (progn
                      (setq split-rows (cons current-row split-rows))
                      (setq current-row (list current-item)))
                    (setq current-row (append current-row (list current-item)))
                  )
                  (setq last-item-x current-item-x)
                )
                (setq split-rows (cons current-row split-rows))
              )
            )
          )
          (setq rows (reverse split-rows))

          (setq rows
            (vl-sort
              rows
              '(lambda (a b / ay by ax bx)
                 (setq ay (aa:gty-get-item-y (car a))
                       by (aa:gty-get-item-y (car b))
                       ax (aa:gty-get-item-x (car a))
                       bx (aa:gty-get-item-x (car b)))
                 (if (> (abs (- ay by)) row-tol)
                   (> ay by)
                   (< ax bx)))))

          (setq anchor-x (aa:gty-get-item-x (car text-data))
                anchor-y (aa:gty-get-item-y (car text-data)))
          (foreach current-item text-data
            (if (< (aa:gty-get-item-x current-item) anchor-x)
              (setq anchor-x (aa:gty-get-item-x current-item))
            )
            (if (> (aa:gty-get-item-y current-item) anchor-y)
              (setq anchor-y (aa:gty-get-item-y current-item))
            )
          )

          (setq col-widths '())
          (foreach row rows
            (setq col-index 0)
            (foreach current-item row
              (if (>= col-index (length col-widths))
                (setq col-widths
                  (append col-widths (list (max (aa:gty-get-item-width current-item) col-gap))))
                (if (> (aa:gty-get-item-width current-item) (nth col-index col-widths))
                  (setq col-widths
                    (aa:gty-update-nth col-index (aa:gty-get-item-width current-item) col-widths))
                )
              )
              (setq col-index (1+ col-index))
            )
          )

          (setq sort-keys '()
                row-map   '()
                row-index 0)
          (foreach row rows
            (setq token     (aa:gty-build-sort-key row row-index)
                  sort-keys (cons token sort-keys)
                  row-map   (cons (cons token row) row-map)
                  row-index (1+ row-index))
          )
          (setq sorted-rows
            (mapcar
              '(lambda (key) (cdr (assoc key row-map)))
              (acad_strlsort sort-keys)))

          (setq row-index 0)
          (foreach row sorted-rows
            (setq current-item-x anchor-x
                  col-index      0)
            (foreach current-item row
              (aa:gty-move-entity
                (aa:gty-get-item-ename current-item)
                (aa:gty-get-item-pt current-item)
                (list current-item-x
                      (- anchor-y (* row-index line-height))
                      (aa:gty-get-item-z current-item)))
              (setq current-item-x (+ current-item-x (nth col-index col-widths) col-gap)
                    col-index      (1+ col-index))
            )
            (setq row-index (1+ row-index))
          )

          (vla-EndUndoMark doc)
          (setq undo-started nil)
          (princ "\n[GTY] Cable text organized.")
        )
        (princ "\n[GTY] No text selected.")
      )
      (sssetfirst nil nil)
      (princ)
    )

    (setq *ys-module-text_tools-loaded* T)
    (princ "\n[YS-Tools] text-tools.lsp loaded.")
  )
)
(princ)
;;; ----- END YS-Tools/modules/text-tools.lsp -----

;;; ----- BEGIN YS-Tools/modules/align-tools.lsp -----
;;; YS-Tools v1.5.0 module
;;; Encoding: GBK/ANSI, CRLF

(if (and (boundp '*ys-module-align_tools-loaded*)
         *ys-module-align_tools-loaded*)
  (princ)
  (progn
    (vl-catch-all-apply 'vl-load-com '())

    (defun aa:get-dxf-point (ed code / v y z)
      (setq v (if (assoc code ed) (cdr (assoc code ed)) nil)
            y (if (assoc (+ code 10) ed) (cdr (assoc (+ code 10) ed)) 0.0)
            z (if (assoc (+ code 20) ed) (cdr (assoc (+ code 20) ed)) 0.0))
      (cond
        ((listp v)
         (list (float (car v))
               (float (cadr v))
               (float (if (caddr v) (caddr v) 0.0))))
        ((numberp v)
         (list (float v)
               (float y)
               (float z)))
      )
    )

    (defun aa:set-dxf-int (ed code value / row)
      (setq row (assoc code ed))
      (if row
        (subst (cons code value) row ed)
        (append ed (list (cons code value))))
    )

    (defun aa:set-dxf-point (ed code pt / row)
      (setq row (assoc code ed))
      (if row
        (subst (list code (car pt) (cadr pt) (caddr pt)) row ed)
        (append ed (list (list code (car pt) (cadr pt) (caddr pt)))))
    )

    (defun aa:text-anchor-point (ed / typ h v)
      (setq typ (cdr (assoc 0 ed)))
      (cond
        ((= typ "TEXT")
         (setq h (if (assoc 72 ed) (cdr (assoc 72 ed)) 0)
               v (if (assoc 73 ed) (cdr (assoc 73 ed)) 0))
         (if (or (/= h 0) (/= v 0))
           (or (aa:get-dxf-point ed 11)
               (aa:get-dxf-point ed 10))
           (aa:get-dxf-point ed 10)))
        ((= typ "MTEXT")
         (aa:get-dxf-point ed 10))
      )
    )

    (defun aa:mtext-center-attachment (ap)
      (cond
        ((member ap '(1 2 3)) 2)
        ((member ap '(4 5 6)) 5)
        ((member ap '(7 8 9)) 8)
        (T 5))
    )

    (defun aa:center-text-by-anchor (ename base-x / ed typ pt v ap new-pt ok)
      (setq ed  (entget ename)
            typ (if ed (cdr (assoc 0 ed)) nil)
            pt  (aa:text-anchor-point ed))
      (if (and ed pt)
        (progn
          (setq new-pt (list base-x (cadr pt) (caddr pt)))
          (cond
            ((= typ "TEXT")
             (setq v  (if (assoc 73 ed) (cdr (assoc 73 ed)) 0)
                   ed (aa:set-dxf-int ed 72 1)
                   ed (aa:set-dxf-int ed 73 v)
                   ed (aa:set-dxf-point ed 10 new-pt)
                   ed (aa:set-dxf-point ed 11 new-pt)))
            ((= typ "MTEXT")
             (setq ap (if (assoc 71 ed) (cdr (assoc 71 ed)) 1)
                   ed (aa:set-dxf-int ed 71 (aa:mtext-center-attachment ap))
                   ed (aa:set-dxf-point ed 10 new-pt)))
          )
          (setq ok (entmod ed))
          (if ok
            (progn
              (entupd ename)
              T)
            nil))
        nil)
    )

    (defun aa:text-raw-v (ed)
      (if (assoc 73 ed) (cdr (assoc 73 ed)) 0)
    )

    (defun aa:text-normalized-h (ed / h)
      (setq h (if (assoc 72 ed) (cdr (assoc 72 ed)) 0))
      (cond
        ((= h 2) 2)
        ((member h '(1 4)) 1)
        (T 0))
    )

    (defun aa:mtext-h-tier (ap)
      (+ 1 (rem (max 0 (1- ap)) 3))
    )

    (defun aa:mtext-v-tier (ap)
      (+ 1 (fix (/ (max 0 (1- ap)) 3)))
    )

    (defun aa:mtext-attachment (h-tier v-tier)
      (+ h-tier (* (1- v-tier) 3))
    )

    (defun aa:set-text-horizontal-align (ename base-x mode / ed typ pt v ap vtier new-pt ok)
      (setq ed  (entget ename)
            typ (if ed (cdr (assoc 0 ed)) nil)
            pt  (aa:text-anchor-point ed))
      (if (and ed pt)
        (progn
          (setq new-pt (list base-x (cadr pt) (caddr pt)))
          (cond
            ((= typ "TEXT")
             (setq v  (aa:text-raw-v ed)
                   ed (aa:set-dxf-int ed 72
                                      (cond
                                        ((= mode 3) 2)
                                        ((= mode 2) 1)
                                        (T 0)))
                   ed (aa:set-dxf-int ed 73 v)
                   ed (aa:set-dxf-point ed 10 new-pt)
                   ed (aa:set-dxf-point ed 11 new-pt)))
            ((= typ "MTEXT")
             (setq ap    (if (assoc 71 ed) (cdr (assoc 71 ed)) 1)
                   vtier (aa:mtext-v-tier ap)
                   ed    (aa:set-dxf-int ed 71 (aa:mtext-attachment mode vtier))
                   ed    (aa:set-dxf-point ed 10 new-pt)))
          )
          (setq ok (entmod ed))
          (if ok
            (progn
              (entupd ename)
              T)
            nil))
        nil)
    )

    (defun aa:set-text-vertical-align (ename base-y mode / ed typ pt h ap htier new-pt ok)
      (setq ed  (entget ename)
            typ (if ed (cdr (assoc 0 ed)) nil)
            pt  (aa:text-anchor-point ed))
      (if (and ed pt)
        (progn
          (setq new-pt (list (car pt) base-y (caddr pt)))
          (cond
            ((= typ "TEXT")
             (setq h  (aa:text-normalized-h ed)
                   ed (aa:set-dxf-int ed 72 h)
                   ed (aa:set-dxf-int ed 73
                                      (cond
                                        ((= mode 1) 3)
                                        ((= mode 2) 2)
                                        (T 1)))
                   ed (aa:set-dxf-point ed 10 new-pt)
                   ed (aa:set-dxf-point ed 11 new-pt)))
            ((= typ "MTEXT")
             (setq ap    (if (assoc 71 ed) (cdr (assoc 71 ed)) 1)
                   htier (aa:mtext-h-tier ap)
                   ed    (aa:set-dxf-int ed 71 (aa:mtext-attachment htier mode))
                   ed    (aa:set-dxf-point ed 10 new-pt)))
          )
          (setq ok (entmod ed))
          (if ok
            (progn
              (entupd ename)
              T)
            nil))
        nil)
    )

    (defun aa:find-ref-by-top-anchor (ss / i ename ed pt ref-ename ref-pt)
      (setq i 0
            ref-ename nil
            ref-pt nil)
      (repeat (sslength ss)
        (setq ename (ssname ss i)
              ed    (entget ename)
              pt    (aa:text-anchor-point ed))
        (if pt
          (if (or (null ref-pt)
                  (> (cadr pt) (cadr ref-pt)))
            (setq ref-ename ename
                  ref-pt    pt))
        )
        (setq i (1+ i))
      )
      (if ref-pt
        (list ref-ename ref-pt))
    )

    (defun aa:find-ref-by-left-anchor (ss / i ename ed pt ref-ename ref-pt)
      (setq i 0
            ref-ename nil
            ref-pt nil)
      (repeat (sslength ss)
        (setq ename (ssname ss i)
              ed    (entget ename)
              pt    (aa:text-anchor-point ed))
        (if pt
          (if (or (null ref-pt)
                  (< (car pt) (car ref-pt)))
            (setq ref-ename ename
                  ref-pt    pt))
        )
        (setq i (1+ i))
      )
      (if ref-pt
        (list ref-ename ref-pt))
    )

    (defun c:ZHONG (/ *error* ss doc undo-open i ename ed pt top-ename top-pt base-x changed skipped)
      (vl-load-com)
      (setq doc       (vla-get-activedocument (vlax-get-acad-object))
            undo-open nil
            top-ename nil
            top-pt    nil
            changed   0
            skipped   0)

      (defun *error* (msg)
        (if undo-open
          (vl-catch-all-apply 'vla-endundomark (list doc))
        )
        (if (and msg
                 (/= msg "Function cancelled")
                 (/= msg "quit / exit abort"))
          (princ (strcat "\n[ZHONG] Error: " msg))
        )
        (princ)
      )

      (princ "\n[ZHONG] Select text objects to center align...")
      (if (setq ss (ssget '((0 . "TEXT,MTEXT"))))
        (progn
          (setq i 0)
          (repeat (sslength ss)
            (setq ename (ssname ss i)
                  ed    (entget ename)
                  pt    (aa:text-anchor-point ed))
            (if pt
              (if (or (null top-pt)
                      (> (cadr pt) (cadr top-pt)))
                (setq top-ename ename
                      top-pt    pt))
              (setq skipped (1+ skipped))
            )
            (setq i (1+ i))
          )

          (if top-pt
            (progn
              (setq base-x (car top-pt))
              (vla-startundomark doc)
              (setq undo-open T
                    i         0)
              (repeat (sslength ss)
                (setq ename (ssname ss i))
                (if (eq ename top-ename)
                  nil
                  (if (aa:center-text-by-anchor ename base-x)
                    (setq changed (1+ changed))
                    (setq skipped (1+ skipped))
                  )
                )
                (setq i (1+ i))
              )
              (vla-endundomark doc)
              (setq undo-open nil)
              (princ
                (strcat
                  "\n[ZHONG] Done. Base X: "
                  (rtos base-x 2 4)
                  ", changed: "
                  (itoa changed)
                  ", skipped: "
                  (itoa skipped)
                  "."))
            )
            (princ "\n[ZHONG] No valid text anchor found in selection.")
          )
        )
        (princ "\n[ZHONG] No text objects selected.")
      )
      (princ)
    )

    (defun c:ZUO (/ *error* ss doc undo-open ref i ename base-x changed skipped)
      (vl-load-com)
      (setq doc       (vla-get-activedocument (vlax-get-acad-object))
            undo-open nil
            changed   0
            skipped   0)

      (defun *error* (msg)
        (if undo-open
          (vl-catch-all-apply 'vla-endundomark (list doc))
        )
        (if (and msg
                 (/= msg "Function cancelled")
                 (/= msg "quit / exit abort"))
          (princ (strcat "\n[ZUO] Error: " msg))
        )
        (princ)
      )

      (princ "\n[ZUO] Select text objects to left align...")
      (if (setq ss (ssget '((0 . "TEXT,MTEXT"))))
        (if (setq ref (aa:find-ref-by-top-bbox doc ss))
          (progn
            (setq base-x (aa:bbox-left-x (cadr ref)))
            (vla-startundomark doc)
            (setq undo-open T
                  i         0)
            (repeat (sslength ss)
              (setq ename (ssname ss i))
              (if (eq ename (car ref))
                nil
                (if (aa:align-text-horizontal-by-bbox doc ename base-x 1)
                  (setq changed (1+ changed))
                  (setq skipped (1+ skipped))
                )
              )
              (setq i (1+ i))
            )
            (vla-endundomark doc)
            (setq undo-open nil)
            (princ
              (strcat
                "\n[ZUO] Done. Base X: "
                (rtos base-x 2 4)
                ", changed: "
                (itoa changed)
                ", skipped: "
                (itoa skipped)
                "."))
          )
          (princ "\n[ZUO] No valid text extents found in selection.")
        )
        (princ "\n[ZUO] No text objects selected.")
      )
      (princ)
    )

    (defun c:YOU (/ *error* ss doc undo-open ref i ename base-x changed skipped)
      (vl-load-com)
      (setq doc       (vla-get-activedocument (vlax-get-acad-object))
            undo-open nil
            changed   0
            skipped   0)

      (defun *error* (msg)
        (if undo-open
          (vl-catch-all-apply 'vla-endundomark (list doc))
        )
        (if (and msg
                 (/= msg "Function cancelled")
                 (/= msg "quit / exit abort"))
          (princ (strcat "\n[YOU] Error: " msg))
        )
        (princ)
      )

      (princ "\n[YOU] Select text objects to right align...")
      (if (setq ss (ssget '((0 . "TEXT,MTEXT"))))
        (if (setq ref (aa:find-ref-by-top-bbox doc ss))
          (progn
            (setq base-x (aa:bbox-right-x (cadr ref)))
            (vla-startundomark doc)
            (setq undo-open T
                  i         0)
            (repeat (sslength ss)
              (setq ename (ssname ss i))
              (if (eq ename (car ref))
                nil
                (if (aa:align-text-horizontal-by-bbox doc ename base-x 3)
                  (setq changed (1+ changed))
                  (setq skipped (1+ skipped))
                )
              )
              (setq i (1+ i))
            )
            (vla-endundomark doc)
            (setq undo-open nil)
            (princ
              (strcat
                "\n[YOU] Done. Base X: "
                (rtos base-x 2 4)
                ", changed: "
                (itoa changed)
                ", skipped: "
                (itoa skipped)
                "."))
          )
          (princ "\n[YOU] No valid text extents found in selection.")
        )
        (princ "\n[YOU] No text objects selected.")
      )
      (princ)
    )

    (defun c:SHANG (/ *error* ss doc undo-open ref i ename base-y changed skipped)
      (vl-load-com)
      (setq doc       (vla-get-activedocument (vlax-get-acad-object))
            undo-open nil
            changed   0
            skipped   0)

      (defun *error* (msg)
        (if undo-open
          (vl-catch-all-apply 'vla-endundomark (list doc))
        )
        (if (and msg
                 (/= msg "Function cancelled")
                 (/= msg "quit / exit abort"))
          (princ (strcat "\n[SHANG] Error: " msg))
        )
        (princ)
      )

      (princ "\n[SHANG] Select text objects to top align...")
      (if (setq ss (ssget '((0 . "TEXT,MTEXT"))))
        (if (setq ref (aa:find-ref-by-left-bbox doc ss))
          (progn
            (setq base-y (aa:bbox-top-y (cadr ref)))
            (vla-startundomark doc)
            (setq undo-open T
                  i         0)
            (repeat (sslength ss)
              (setq ename (ssname ss i))
              (if (eq ename (car ref))
                nil
                (if (aa:align-text-vertical-by-bbox doc ename base-y 1)
                  (setq changed (1+ changed))
                  (setq skipped (1+ skipped))
                )
              )
              (setq i (1+ i))
            )
            (vla-endundomark doc)
            (setq undo-open nil)
            (princ
              (strcat
                "\n[SHANG] Done. Base Y: "
                (rtos base-y 2 4)
                ", changed: "
                (itoa changed)
                ", skipped: "
                (itoa skipped)
                "."))
          )
          (princ "\n[SHANG] No valid text extents found in selection.")
        )
        (princ "\n[SHANG] No text objects selected.")
      )
      (princ)
    )

    (defun c:XIA (/ *error* ss doc undo-open ref i ename base-y changed skipped)
      (vl-load-com)
      (setq doc       (vla-get-activedocument (vlax-get-acad-object))
            undo-open nil
            changed   0
            skipped   0)

      (defun *error* (msg)
        (if undo-open
          (vl-catch-all-apply 'vla-endundomark (list doc))
        )
        (if (and msg
                 (/= msg "Function cancelled")
                 (/= msg "quit / exit abort"))
          (princ (strcat "\n[XIA] Error: " msg))
        )
        (princ)
      )

      (princ "\n[XIA] Select text objects to bottom align...")
      (if (setq ss (ssget '((0 . "TEXT,MTEXT"))))
        (if (setq ref (aa:find-ref-by-left-bbox doc ss))
          (progn
            (setq base-y (aa:bbox-bottom-y (cadr ref)))
            (vla-startundomark doc)
            (setq undo-open T
                  i         0)
            (repeat (sslength ss)
              (setq ename (ssname ss i))
              (if (eq ename (car ref))
                nil
                (if (aa:align-text-vertical-by-bbox doc ename base-y 3)
                  (setq changed (1+ changed))
                  (setq skipped (1+ skipped))
                )
              )
              (setq i (1+ i))
            )
            (vla-endundomark doc)
            (setq undo-open nil)
            (princ
              (strcat
                "\n[XIA] Done. Base Y: "
                (rtos base-y 2 4)
                ", changed: "
                (itoa changed)
                ", skipped: "
                (itoa skipped)
                "."))
          )
          (princ "\n[XIA] No valid text extents found in selection.")
        )
        (princ "\n[XIA] No text objects selected.")
      )
      (princ)
    )

    (setq *ys-module-align_tools-loaded* T)
    (princ "\n[YS-Tools] align-tools.lsp loaded.")
  )
)
(princ)
;;; ----- END YS-Tools/modules/align-tools.lsp -----

;;; ----- BEGIN YS-Tools/modules/color-tools.lsp -----
;;; YS-Tools v1.5.0 module
;;; Encoding: GBK/ANSI, CRLF

(if (and (boundp '*ys-module-color_tools-loaded*)
         *ys-module-color_tools-loaded*)
  (princ)
  (progn
    (vl-catch-all-apply 'vl-load-com '())

    (defun c:y (/ targetColor ss i ename)
      (setq targetColor *Y_TextColor*) ; 从配置区获取颜色
      (princ "\n选择要改变颜色的对象: ")
      (setq ss (ssget))

      (if ss
        (progn
          (setq i 0)
          (repeat (sslength ss)
            (setq ename (ssname ss i))
            (vla-put-Color (vlax-ename->vla-object ename) targetColor)
            (setq i (1+ i))
          )
          (princ (strcat "\n所有选中的对象颜色已更改。"))
        )
        (princ "\n没有选中任何对象。")
      )
      (princ)
    )

    (defun c:RR (/ targetColor ss i ename)
      (setq targetColor *RR_TextColor*) ; 从配置区获取颜色
      (princ "\n选择要改为红色的对象: ")
      (setq ss (ssget))

      (if ss
        (progn
          (setq i 0)
          (repeat (sslength ss)
            (setq ename (ssname ss i))
            (vla-put-Color (vlax-ename->vla-object ename) targetColor)
            (setq i (1+ i))
          )
          (princ "\n所有选中的对象已改为红色。")
        )
        (princ "\n没有选中任何对象。")
      )
      (princ)
    )

    (defun c:UU (/ targetColor ss i ename)
      (setq targetColor *UU_TextColor*) ; 从配置区获取颜色
      (princ "\n选择要改为白色的对象: ")
      (setq ss (ssget))

      (if ss
        (progn
          (setq i 0)
          (repeat (sslength ss)
            (setq ename (ssname ss i))
            (vla-put-Color (vlax-ename->vla-object ename) targetColor)
            (setq i (1+ i))
          )
          (princ "\n所有选中的对象已改为白色。")
        )
        (princ "\n没有选中任何对象。")
      )
      (princ)
    )

    (defun c:GG (/ targetColor ss i ename)
      (setq targetColor *GG_TextColor*) ; 从配置区获取颜色
      (princ "\n选择要改为绿色的对象: ")
      (setq ss (ssget))

      (if ss
        (progn
          (setq i 0)
          (repeat (sslength ss)
            (setq ename (ssname ss i))
            (vla-put-Color (vlax-ename->vla-object ename) targetColor)
            (setq i (1+ i))
          )
          (princ "\n所有选中的对象已改为绿色。")
        )
        (princ "\n没有选中任何对象。")
      )
      (princ)
    )

    (setq *ys-module-color_tools-loaded* T)
    (princ "\n[YS-Tools] color-tools.lsp loaded.")
  )
)
(princ)
;;; ----- END YS-Tools/modules/color-tools.lsp -----

;;; ----- BEGIN YS-Tools/modules/move-tools.lsp -----
;;; YS-Tools v1.5.0 module
;;; Encoding: GBK/ANSI, CRLF

(if (and (boundp '*ys-module-move_tools-loaded*)
         *ys-module-move_tools-loaded*)
  (princ)
  (progn
    (vl-catch-all-apply 'vl-load-com '())

    (defun c:SYI (/ ss)
      (setq ss (ssget "_:L"))
      (if ss
        (command "_.MOVE" ss "" "0,0,0" "0,5,0")
        (princ "\n未选择任何对象。")
      )
      (princ)
    )

    (defun c:XYI (/ ss)
      (setq ss (ssget "_:L"))
      (if ss
        (command "_.MOVE" ss "" "0,0,0" "0,-5,0")
        (princ "\n未选择任何对象。")
      )
      (princ)
    )

    (defun c:ZYI (/ ss)
      (setq ss (ssget "_:L"))
      (if ss
        (command "_.MOVE" ss "" "0,0,0" "-5,0,0")
        (princ "\n未选择任何对象。")
      )
      (princ)
    )

    (defun c:YYI (/ ss)
      (setq ss (ssget "_:L"))
      (if ss
        (command "_.MOVE" ss "" "0,0,0" "5,0,0")
        (princ "\n未选择任何对象。")
      )
      (princ)
    )

    (setq *ys-module-move_tools-loaded* T)
    (princ "\n[YS-Tools] move-tools.lsp loaded.")
  )
)
(princ)
;;; ----- END YS-Tools/modules/move-tools.lsp -----

;;; ----- BEGIN YS-Tools/modules/line-tools.lsp -----
;;; YS-Tools v1.5.0 module
;;; Encoding: GBK/ANSI, CRLF

(if (and (boundp '*ys-module-line_tools-loaded*)
         *ys-module-line_tools-loaded*)
  (princ)
  (progn
    (vl-catch-all-apply 'vl-load-com '())

    (defun c:LONG (/ ss total-length index ename obj)
      (prompt "\n请选择要计算总长度的多段线: ")
      (setq ss (ssget '((0 . "POLYLINE,LWPOLYLINE"))))
      (if ss
        (progn
          (setq total-length 0.0 index 0)
          (repeat (sslength ss)
            (setq ename (ssname ss index))
            (setq obj (vlax-ename->vla-object ename))
            (setq total-length (+ total-length (vla-get-length obj)))
            (setq index (1+ index))
          )
          (prompt (strcat "\n所选多段线的总长度为: " (rtos total-length)))
        )
        (prompt "\n未选择任何多段线。")
      )
      (princ)
    )

    (defun c:YAN (/ *error* doc group_num extend_dir ss ent_list sorted_list i ent p10 p11 p10y p11y multiplier delta new_y new_pt obj)

      ;; --- 错误处理函数 ---
      (defun *error* (msg)
        (if (and msg (not (wcmatch (strcase msg) "*BREAK*,*CANCEL*,*EXIT*")))
          (princ (strcat "\n错误: " msg))
        )
        (if (= (type doc) 'vla-object) (vla-EndUndoMark doc))
        (princ)
      )

      (vl-load-com)
      (setq doc (vla-get-ActiveDocument (vlax-get-acad-object)))

      ;; --- 1. 获取用户输入选项 ---

      ;; 初始化选项：分组数量 (2 或 4)
      (initget 1 "2 4")
      (setq group_num (atoi (getkword "\n请输入分组数量 [2/4]: ")))

      ;; 初始化选项：延伸方向 (Up 或 Down)
      (initget 1 "Up Down")
      (setq extend_dir (getkword "\n请输入延伸方向 [向上(Up)/向下(Down)]: "))

      ;; --- 2. 选择对象 ---
      (princ "\n请选择竖直直线 (从左到右将自动排序): ")
      (setq ss (ssget '((0 . "LINE"))))

      (if ss
        (progn
          (vla-StartUndoMark doc)

          ;; --- 3. 将选择集转换为图元列表 ---
          (setq ent_list '())
          (setq i 0)
          (repeat (sslength ss)
            (setq ent_list (cons (ssname ss i) ent_list))
            (setq i (1+ i))
          )

          ;; --- 4. 从左到右排序 ---
          ;; 依据组码10 (起点) 的 X 坐标进行排序
          (setq sorted_list
            (vl-sort ent_list
              '(lambda (e1 e2)
                 (< (car (cdr (assoc 10 (entget e1))))
                    (car (cdr (assoc 10 (entget e2)))))
               )
            )
          )

          ;; --- 5. 循环处理每一条线 ---
          (setq i 0) ;; 重置计数器作为列表索引
          (foreach ent sorted_list
            (setq obj (entget ent))
            (setq p10 (cdr (assoc 10 obj))) ;; 起点坐标 (X Y Z)
            (setq p11 (cdr (assoc 11 obj))) ;; 终点坐标 (X Y Z)

            ;; 计算当前的倍数
            ;; 逻辑：索引除以组数取整，然后+1
            ;; 例如组数为2：0,1 -> 倍数1; 2,3 -> 倍数2
            (setq multiplier (1+ (fix (/ i group_num))))
            (setq delta (* multiplier 5))

            (setq p10y (cadr p10))
            (setq p11y (cadr p11))

            ;; 根据方向修改坐标
            (if (eq extend_dir "Down")
              ;; --- 向下延伸 ---
              ;; 逻辑：找到Y值较小的那个点，将其Y值减去delta
              (if (< p10y p11y)
                (progn
                  ;; p10 是下端点
                  (setq new_y (- p10y delta))
                  (setq new_pt (list (car p10) new_y (caddr p10)))
                  (setq obj (subst (cons 10 new_pt) (assoc 10 obj) obj))
                )
                (progn
                  ;; p11 是下端点
                  (setq new_y (- p11y delta))
                  (setq new_pt (list (car p11) new_y (caddr p11)))
                  (setq obj (subst (cons 11 new_pt) (assoc 11 obj) obj))
                )
              )
              ;; --- 向上延伸 ---
              ;; 逻辑：找到Y值较大的那个点，将其Y值加上delta
              (if (> p10y p11y)
                (progn
                  ;; p10 是上端点
                  (setq new_y (+ p10y delta))
                  (setq new_pt (list (car p10) new_y (caddr p10)))
                  (setq obj (subst (cons 10 new_pt) (assoc 10 obj) obj))
                )
                (progn
                  ;; p11 是上端点
                  (setq new_y (+ p11y delta))
                  (setq new_pt (list (car p11) new_y (caddr p11)))
                  (setq obj (subst (cons 11 new_pt) (assoc 11 obj) obj))
                )
              )
            )

            ;; 更新图元
            (entmod obj)

            ;; 增加索引
            (setq i (1+ i))
          )

          (vla-EndUndoMark doc)
          (princ (strcat "\n完成! 共处理了 " (itoa (length sorted_list)) " 条直线。"))
        )
        (princ "\n未选择任何对象。")
      )
      (princ)
    )

    (defun c:SYAN (/ ss i ent p1 p2 high low ang new_high)
      (princ "\n请选择要向上延长的直线...")
      ;; 仅选择直线(LINE)
      (if (setq ss (ssget '((0 . "LINE"))))
        (progn
          (setq i 0)
          (repeat (sslength ss)
            (setq ent (entget (ssname ss i)))
            (setq p1 (cdr (assoc 10 ent))) ; 起点
            (setq p2 (cdr (assoc 11 ent))) ; 终点

            ;; 比较 Y 坐标，确定哪一个点在上方
            (if (> (cadr p1) (cadr p2))
              (setq high p1 low p2)
              (setq high p2 low p1)
            )

            ;; 计算从低点到高点的角度
            (setq ang (angle low high))
            ;; 在高点位置沿角度方向延长 5
            (setq new_high (polar high ang 5))

            ;; 更新实体数据
            (if (equal high p1)
              (setq ent (subst (cons 10 new_high) (assoc 10 ent) ent))
              (setq ent (subst (cons 11 new_high) (assoc 11 ent) ent))
            )

            (entmod ent) ; 修改实体
            (setq i (1+ i))
          )
          (princ (strcat "\n成功向上延长了 " (itoa i) " 条直线。"))
        )
        (princ "\n未选中任何直线。")
      )
      (princ)
    )

    (defun c:XYAN (/ ss i ent p1 p2 high low ang new_low)
      (princ "\n请选择要向下延长的直线...")
      ;; 仅选择直线(LINE)
      (if (setq ss (ssget '((0 . "LINE"))))
        (progn
          (setq i 0)
          (repeat (sslength ss)
            (setq ent (entget (ssname ss i)))
            (setq p1 (cdr (assoc 10 ent)))
            (setq p2 (cdr (assoc 11 ent)))

            ;; 比较 Y 坐标，确定哪一个点在下方
            (if (< (cadr p1) (cadr p2))
              (setq low p1 high p2)
              (setq low p2 high p1)
            )

            ;; 计算从高点到低点的角度
            (setq ang (angle high low))
            ;; 在低点位置沿角度方向延长 5
            (setq new_low (polar low ang 5))

            ;; 更新实体数据
            (if (equal low p1)
              (setq ent (subst (cons 10 new_low) (assoc 10 ent) ent))
              (setq ent (subst (cons 11 new_low) (assoc 11 ent) ent))
            )

            (entmod ent) ; 修改实体
            (setq i (1+ i))
          )
          (princ (strcat "\n成功向下延长了 " (itoa i) " 条直线。"))
        )
        (princ "\n未选中任何直线。")
      )
      (princ)
    )

    (defun c:XSUO ( / ss i ent entdata p10 p11 low_pt high_pt dx dy dz len ux uy uz new_pt is_p10_low )
      (princ "\n【XSUO】请选择要【从下往上】缩短 5 单位的直线...")
      (setq ss (ssget '((0 . "LINE"))))

      (if ss
        (progn
          (command "_.UNDO" "_Begin")
          (setq i 0)
          (repeat (sslength ss)
            (setq ent (ssname ss i))
            (setq entdata (entget ent))
            (setq p10 (cdr (assoc 10 entdata)))
            (setq p11 (cdr (assoc 11 entdata)))

            (if (< (cadr p10) (cadr p11))
              (setq low_pt p10 high_pt p11 is_p10_low T)
              (setq low_pt p11 high_pt p10 is_p10_low nil)
            )

            (setq dx (- (car high_pt) (car low_pt))
                  dy (- (cadr high_pt) (cadr low_pt))
                  dz (- (caddr high_pt) (caddr low_pt))
                  len (sqrt (+ (* dx dx) (* dy dy) (* dz dz))))

            (if (> len 5.01)
              (progn
                (setq ux (/ dx len) uy (/ dy len) uz (/ dz len))
                (setq new_pt (list (+ (car low_pt) (* 5.0 ux))
                                   (+ (cadr low_pt) (* 5.0 uy))
                                   (+ (caddr low_pt) (* 5.0 uz))))
                (if is_p10_low
                  (setq entdata (subst (cons 10 new_pt) (assoc 10 entdata) entdata))
                  (setq entdata (subst (cons 11 new_pt) (assoc 11 entdata) entdata))
                )
                (entmod entdata)
                (entupd ent)
              )
              (princ (strcat "\n第 " (itoa (1+ i)) " 条线太短，已跳过。"))
            )
            (setq i (1+ i))
          )
          (command "_.UNDO" "_End")
          (princ (strcat "\nXSUO 完成！共处理 " (itoa (sslength ss)) " 条直线。"))
        )
        (princ "\n未选择直线，命令结束。")
      )
      (princ)
    )

    (defun c:SSUO ( / ss i ent entdata p10 p11 low_pt high_pt dx dy dz len ux uy uz new_pt is_p10_low )
      (princ "\n【SSUO】请选择要【从上往下】缩短 5 单位的直线...")
      (setq ss (ssget '((0 . "LINE"))))

      (if ss
        (progn
          (command "_.UNDO" "_Begin")
          (setq i 0)
          (repeat (sslength ss)
            (setq ent (ssname ss i))
            (setq entdata (entget ent))
            (setq p10 (cdr (assoc 10 entdata)))
            (setq p11 (cdr (assoc 11 entdata)))

            (if (< (cadr p10) (cadr p11))
              (setq low_pt p10 high_pt p11 is_p10_low T)
              (setq low_pt p11 high_pt p10 is_p10_low nil)
            )

            (setq dx (- (car high_pt) (car low_pt))
                  dy (- (cadr high_pt) (cadr low_pt))
                  dz (- (caddr high_pt) (caddr low_pt))
                  len (sqrt (+ (* dx dx) (* dy dy) (* dz dz))))

            (if (> len 5.01)
              (progn
                (setq ux (/ dx len) uy (/ dy len) uz (/ dz len))
                (setq new_pt (list (- (car high_pt) (* 5.0 ux))
                                   (- (cadr high_pt) (* 5.0 uy))
                                   (- (caddr high_pt) (* 5.0 uz))))
                (if is_p10_low
                  (setq entdata (subst (cons 11 new_pt) (assoc 11 entdata) entdata))
                  (setq entdata (subst (cons 10 new_pt) (assoc 10 entdata) entdata))
                )
                (entmod entdata)
                (entupd ent)
              )
              (princ (strcat "\n第 " (itoa (1+ i)) " 条线太短，已跳过。"))
            )
            (setq i (1+ i))
          )
          (command "_.UNDO" "_End")
          (princ (strcat "\nSSUO 完成！共处理 " (itoa (sslength ss)) " 条直线。"))
        )
        (princ "\n未选择直线，命令结束。")
      )
      (princ)
    )

    (defun c:SJ (/ ss i ent ed p1 p2 top sp ep)
      (princ "\n=== SJ 上接模式 ===")

      (if (setq ss (ssget '((0 . "LINE"))))
        (progn
          (setq i 0)
          (repeat (sslength ss)
            (setq ent (ssname ss i)
                  ed  (entget ent)
                  p1  (cdr (assoc 10 ed))
                  p2  (cdr (assoc 11 ed)))
            (setq top (if (> (cadr p1) (cadr p2)) p1 p2))
            (setq sp (list (+ (car top) 1.0) (cadr top) (caddr top))
                  ep (list (car top) (- (cadr top) 1.0) (caddr top)))
            (command "._LINE" "_non" sp "_non" ep "")
            (setq i (1+ i))
          )
          (princ (strcat "\n已成功为 " (itoa (sslength ss)) " 条直线绘制【上接】短线！"))
        )
        (princ "\n未选中直线！请框选直线后再输入 SJ")
      )
      (princ)
    )

    (defun c:XJ (/ ss i ent ed p1 p2 bot sp ep)
      (princ "\n=== XJ 下接模式 ===")

      (if (setq ss (ssget '((0 . "LINE"))))
        (progn
          (setq i 0)
          (repeat (sslength ss)
            (setq ent (ssname ss i)
                  ed  (entget ent)
                  p1  (cdr (assoc 10 ed))
                  p2  (cdr (assoc 11 ed)))
            (setq bot (if (< (cadr p1) (cadr p2)) p1 p2))
            (setq sp (list (+ (car bot) 1.0) (cadr bot) (caddr bot))
                  ep (list (car bot) (+ (cadr bot) 1.0) (caddr bot)))
            (command "._LINE" "_non" sp "_non" ep "")
            (setq i (1+ i))
          )
          (princ (strcat "\n已成功为 " (itoa (sslength ss)) " 条直线绘制【下接】短线！"))
        )
        (princ "\n未选中直线！请框选直线后再输入 XJ")
      )
      (princ)
    )

    (setq *ys-module-line_tools-loaded* T)
    (princ "\n[YS-Tools] line-tools.lsp loaded.")
  )
)
(princ)
;;; ----- END YS-Tools/modules/line-tools.lsp -----

;;; ----- BEGIN YS-Tools/modules/draw-tools.lsp -----
;;; YS-Tools v1.5.0 module
;;; Encoding: GBK/ANSI, CRLF

(if (and (boundp '*ys-module-draw_tools-loaded*)
         *ys-module-draw_tools-loaded*)
  (princ)
  (progn
    (vl-catch-all-apply 'vl-load-com '())

    (defun c:EXCEL (/ rows cols totalWidth totalHeight startPoint
                     cellWidth cellHeight i j x1 y1 x2 y2)
      (princ "\n*** 表格绘制工具 (快捷键: EXCEL) ***")
      (initget 7) (setq rows (getint "\n请输入表格的行数: "))
      (initget 7) (setq cols (getint "\n请输入表格的列数: "))
      (initget 7) (setq totalWidth (getreal "\n请输入表格的总宽度: "))
      (initget 7) (setq totalHeight (getreal "\n请输入表格的总高度: "))
      (setq startPoint (getpoint "\n请选择表格的插入点: "))

      (setq cellWidth (/ totalWidth cols))
      (setq cellHeight (/ totalHeight rows))

      (command "_.layer" "_m" *EXCEL_LayerName* "_c" *EXCEL_LayerColor* "" "")

      (command "_.line"
               startPoint
               (list (+ (car startPoint) totalWidth) (cadr startPoint))
               (list (+ (car startPoint) totalWidth) (+ (cadr startPoint) totalHeight))
               (list (car startPoint) (+ (cadr startPoint) totalHeight))
               "_close")

      (setq i 1)
      (while (< i rows)
        (setq y1 (+ (cadr startPoint) (* i cellHeight)))
        (setq x1 (car startPoint))
        (setq x2 (+ x1 totalWidth))
        (command "_.line" (list x1 y1) (list x2 y1) "")
        (setq i (1+ i))
      )

      (setq j 1)
      (while (< j cols)
        (setq x1 (+ (car startPoint) (* j cellWidth)))
        (setq y1 (cadr startPoint))
        (setq y2 (+ y1 totalHeight))
        (command "_.line" (list x1 y1) (list x1 y2) "")
        (setq j (1+ j))
      )

      (princ (strcat "\n表格绘制完成! "
                     "行数: " (itoa rows)
                     ", 列数: " (itoa cols)))
      (princ)
    )

    (defun aa:digit-char-p (ch / code)
      (and ch
           (= (type ch) 'STR)
           (= (strlen ch) 1)
           (setq code (ascii ch))
           (<= 48 code 57))
    )

    (defun aa:nu-number-token-at (str start / len idx digit-found end)
      (setq len (strlen str)
            idx start
            digit-found nil
            end nil)
      (if (<= start len)
        (progn
          (if (member (substr str idx 1) '("+" "-"))
            (setq idx (1+ idx)))
          (while (and (<= idx len)
                      (aa:digit-char-p (substr str idx 1)))
            (setq digit-found T
                  end idx
                  idx (1+ idx)))
          (if (and (<= idx len)
                   (= (substr str idx 1) ".")
                   (< idx len)
                   (aa:digit-char-p (substr str (1+ idx) 1)))
            (progn
              (setq idx (1+ idx))
              (while (and (<= idx len)
                          (aa:digit-char-p (substr str idx 1)))
                (setq digit-found T
                      end idx
                      idx (1+ idx)))))
          (if digit-found
            (list start
                  end
                  (substr str start (1+ (- end start)))))
        )
      )
    )

    (defun aa:nu-find-first-number (str / len idx token ch)
      (setq len (strlen str)
            idx 1
            token nil)
      (while (and (<= idx len) (null token))
        (setq ch (substr str idx 1))
        (if (or (aa:digit-char-p ch)
                (and (= ch ".")
                     (< idx len)
                     (aa:digit-char-p (substr str (1+ idx) 1)))
                (and (member ch '("+" "-"))
                     (< idx len)
                     (or (aa:digit-char-p (substr str (1+ idx) 1))
                         (and (< (1+ idx) len)
                              (= (substr str (1+ idx) 1) ".")
                              (aa:digit-char-p (substr str (+ idx 2) 1))))))
          (setq token (aa:nu-number-token-at str idx))
        )
        (if (null token)
          (setq idx (1+ idx))))
      token
    )

    (defun aa:nu-trim-number-string (str)
      (if (vl-string-search "." str)
        (progn
          (while (and (> (strlen str) 0)
                      (= (substr str (strlen str) 1) "0"))
            (setq str (substr str 1 (1- (strlen str)))))
          (if (and (> (strlen str) 0)
                   (= (substr str (strlen str) 1) "."))
            (setq str (substr str 1 (1- (strlen str))))))
      )
      (if (or (= str "") (= str "-0") (= str "+0"))
        "0"
        str)
    )

    (defun aa:nu-string-all-digits-p (str / idx ok)
      (setq idx 1
            ok (> (strlen str) 0))
      (while (and ok (<= idx (strlen str)))
        (if (not (aa:digit-char-p (substr str idx 1)))
          (setq ok nil))
        (setq idx (1+ idx)))
      ok
    )

    (defun aa:nu-format-number (value old-token / raw body keep-plus pad-width abs-str)
      (setq raw (aa:nu-trim-number-string (rtos value 2 8))
            body old-token
            keep-plus nil
            pad-width 0)
      (if (> (strlen body) 0)
        (cond
          ((= (substr body 1 1) "+")
           (setq keep-plus T
                 body (substr body 2)))
          ((= (substr body 1 1) "-")
           (setq body (substr body 2)))
        )
      )
      (if (and (= value (fix value))
               (> (strlen body) 1)
               (= (substr body 1 1) "0")
               (aa:nu-string-all-digits-p body))
        (progn
          (setq pad-width (strlen body)
                abs-str (itoa (abs (fix value))))
          (while (< (strlen abs-str) pad-width)
            (setq abs-str (strcat "0" abs-str)))
          (setq raw
                 (strcat
                   (cond
                     ((< value 0) "-")
                     ((and keep-plus (>= value 0)) "+")
                     (T ""))
                   abs-str)))
        (if (and keep-plus
                 (>= value 0)
                 (/= raw ""))
          (setq raw (strcat "+" raw))))
      raw
    )

    (defun aa:nu-rewrite-text (str delta / token start end old-val new-str)
      (if (setq token (aa:nu-find-first-number str))
        (progn
          (setq start   (car token)
                end     (cadr token)
                old-val (distof (caddr token)))
          (if (numberp old-val)
            (progn
              (setq new-str (aa:nu-format-number (- old-val delta) (caddr token)))
              (strcat
                (if (> start 1)
                  (substr str 1 (1- start))
                  "")
                new-str
                (if (< end (strlen str))
                  (substr str (1+ end))
                  "")))
          )
        )
      )
    )

    (defun c:NU (/ *error* doc undo-open ss a i en ed str new-str changed)
      (vl-load-com)
      (setq doc (vla-get-ActiveDocument (vlax-get-acad-object))
            undo-open nil)

      (defun *error* (msg)
        (if undo-open
          (vl-catch-all-apply 'vla-EndUndoMark (list doc)))
        (if (and msg
                 (not (wcmatch (strcase msg) "*BREAK*,*CANCEL*,*EXIT*,*QUIT*")))
          (princ (strcat "\n[NU] Error: " msg)))
        (princ)
      )

      (if (null (setq a (getreal "\n[NU] Enter value to subtract: ")))
        (princ "\n[NU] No value entered.")
        (progn
          (princ "\n[NU] Select TEXT/MTEXT objects: ")
          (if (setq ss (ssget '((0 . "TEXT,MTEXT"))))
            (progn
              (setq i 0
                    changed 0)
              (vla-StartUndoMark doc)
              (setq undo-open T)
              (repeat (sslength ss)
                (setq en (ssname ss i)
                      ed (entget en)
                      str (cdr (assoc 1 ed))
                      new-str (if str (aa:nu-rewrite-text str a)))
                (if (and new-str (/= new-str str))
                  (progn
                    (setq ed (subst (cons 1 new-str) (assoc 1 ed) ed))
                    (if (entmod ed)
                      (setq changed (1+ changed)))))
                (setq i (1+ i)))
              (vla-EndUndoMark doc)
              (setq undo-open nil)
              (princ (strcat "\n[NU] Updated " (itoa changed) " text object(s)."))
            )
            (princ "\n[NU] No text objects selected.")
          )
        )
      )
      (princ)
    )

    (defun ys:make-eff-poly (p / x y p1 p2 p3 p4 p5 p6)
      (setq x (car p))
      (setq y (cadr p))
      (setq p1 (list x y 0.0))
      (setq p2 (list (+ x 390.0) y 0.0))
      (setq p3 (list (+ x 390.0) (- y 237.0) 0.0))
      (setq p4 (list (+ x 210.0) (- y 237.0) 0.0))
      (setq p5 (list (+ x 210.0) (- y 287.0) 0.0))
      (setq p6 (list x (- y 287.0) 0.0))
      (list p1 p2 p3 p4 p5 p6)
    )

    (defun C:KUANG (/ pt pts)
      (vl-load-com)
      (setq pt (getpoint "\nPick upper-left point for L frame: "))
      (if pt
        (progn
          (setq pts (ys:make-eff-poly pt))
          (command "_.PLINE"
                   (nth 0 pts) "_non"
                   (nth 1 pts) "_non"
                   (nth 2 pts) "_non"
                   (nth 3 pts) "_non"
                   (nth 4 pts) "_non"
                   (nth 5 pts) "_close")
          (princ "\nL frame created. Size: 390x237 + 210x50.")
        )
        (princ "\nCanceled.")
      )
      (princ)
    )

    (setq *ys-module-draw_tools-loaded* T)
    (princ "\n[YS-Tools] draw-tools.lsp loaded.")
  )
)
(princ)
;;; ----- END YS-Tools/modules/draw-tools.lsp -----

;;; ----- BEGIN YS-Tools/modules/cable-tools.lsp -----
;;; YS-Tools v1.5.0 module
;;; Encoding: GBK/ANSI, CRLF

(if (and (boundp '*ys-module-cable_tools-loaded*)
         *ys-module-cable_tools-loaded*)
  (princ)
  (progn
    (vl-catch-all-apply 'vl-load-com '())

    (defun bian-make-text (pt txt sty / data)
      (setq data
        (list
          '(0 . "TEXT")
          '(100 . "AcDbEntity")
          '(100 . "AcDbText")
          (cons 10 pt)
          (cons 40 3.0)
          (cons 1 txt)
          (cons 7 sty)
          '(72 . 0)
          (cons 11 pt)
          '(50 . 0.0)
          '(41 . 0.7)
          '(51 . 0.0)
          '(71 . 0)
          '(73 . 0)
        )
      )
      (entmake data)
    )

    (defun bian-right-point (p1 p2)
      (if (> (car p1) (car p2)) p1 p2)
    )

    (defun bian-draw-one (ed sty / p1 p2 rp oz alt half bp1 bp2)
      (setq p1   (cdr (assoc 10 ed))
            p2   (cdr (assoc 11 ed))
            rp   (bian-right-point p1 p2)
            oz   (list (- (car rp) 40.0) (cadr rp) 0.0)
            alt  (* 2.5 (sqrt 3.0))
            half 2.5
            bp1  (list (- (car oz) alt) (+ (cadr oz) half) 0.0)
            bp2  (list (- (car oz) alt) (- (cadr oz) half) 0.0))

      (entmake
        (list
          '(0 . "LWPOLYLINE")
          '(100 . "AcDbEntity")
          '(100 . "AcDbPolyline")
          '(90 . 3)
          '(70 . 1)
          (cons 10 (list (car oz)  (cadr oz)))
          (cons 10 (list (car bp1) (cadr bp1)))
          (cons 10 (list (car bp2) (cadr bp2)))
        )
      )

      (bian-make-text (list (+ (car oz) 1.5)   (+ (cadr oz) 0.5) 0.0) "\\U+81F3"  sty)
      (bian-make-text (list (+ (car oz) 27.0)  (+ (cadr oz) 0.5) 0.0) "2\\U+00D74" sty)
      (bian-make-text (list (+ (car oz) -20.0) (+ (cadr oz) 0.5) 0.0) "UPS-12"    sty)
    )

    (defun c:BIAN (/ ss i ent ed sty cnt)
      (setq sty (if (tblsearch "STYLE" "HZ") "HZ" (getvar "TEXTSTYLE")))

      (if (setq ss (ssget '((0 . "LINE"))))
        (progn
          (setq i 0
                cnt (sslength ss))
          (repeat cnt
            (setq ent (ssname ss i)
                  ed  (entget ent))
            (bian-draw-one ed sty)
            (setq i (1+ i))
          )
          (if (tblsearch "STYLE" "HZ")
            (princ (strcat "\nBIAN finished for " (itoa cnt) " line(s)."))
            (princ
              (strcat
                "\nBIAN finished for "
                (itoa cnt)
                " line(s); style HZ not found, using current style "
                sty
                "."
              )
            )
          )
        )
        (princ "\nSelect LINE objects before running BIAN.")
      )
      (princ)
    )

    (defun lan-get-option (vert_count move_right / kw)
      (initget "Shang Xia")
      (setq kw
        (getkword
          (strcat "\n检测到 " (itoa vert_count)
                  " 条竖直线，副本将右移 " (rtos move_right 2 0)
                  " 单位。请选择方向 [向上(Shang)/向下(Xia)] <向上>: ")))

      (cond
        ((or (null kw) (equal kw "Shang")) "S")
        ((equal kw "Xia") "X")
      )
    )

    (defun c:LAN ( / ss total_count
                   vert_lines  horiz_lines  diag_lines
                   vert_count  horiz_count  diag_count
                   opt  move_right  dy
                   i  ent  copy_ent  entdata
                   pt1 pt2 new_pt1 new_pt2 )

      ;; 1. 取得选择集
      (setq ss (ssget))
      (if (null ss)
        (progn (princ "\n未选中任何对象。") (exit))
      )

      (setq total_count (sslength ss)
            vert_lines  '()
            horiz_lines '()
            diag_lines  '())

      ;; 2. 分类：竖直线 / 水平线 / 斜线
      (setq i 0)
      (while (< i total_count)
        (setq ent     (ssname ss i)
              entdata (entget ent)
              pt1     (cdr (assoc 10 entdata))
              pt2     (cdr (assoc 11 entdata)))

        (if (and pt1 pt2)
          (cond
            ((< (abs (- (car pt1) (car pt2))) 0.001)
             (setq vert_lines (cons ent vert_lines)))
            ((< (abs (- (cadr pt1) (cadr pt2))) 0.001)
             (setq horiz_lines (cons ent horiz_lines)))
            (T
             (setq diag_lines (cons ent diag_lines)))
          )
        )
        (setq i (1+ i))
      )

      (setq vert_count  (length vert_lines)
            horiz_count (length horiz_lines)
            diag_count  (length diag_lines))

      ;; 3. 校验选择集
      (cond
        ((= vert_count 0)
         (princ "\n错误：未检测到竖直直线，请重新选择。")
         (exit))
        ((/= horiz_count 1)
         (princ (strcat "\n错误：需要恰好 1 条水平直线，当前检测到 "
                        (itoa horiz_count) " 条。"))
         (exit))
        ((/= diag_count vert_count)
         (princ (strcat "\n错误：斜线数量（" (itoa diag_count)
                        "）与竖直线数量（" (itoa vert_count)
                        "）不匹配。"))
         (exit))
      )

      ;; 4. 计算移动量
      (setq move_right (* 5 vert_count))

      ;; 5. 获取 S / X 选项
      (setq opt (lan-get-option vert_count move_right))
      (if (null opt)
        (progn (princ "\n已取消。") (exit)))

      (setq dy (if (equal opt "S") 5.0 -5.0))

      ;; 6. 处理竖直直线：复制 → 右移 move_right → 端点延长 5
      (foreach ent vert_lines
        (setq copy_ent (entmakex (entget ent))
              entdata  (entget copy_ent)
              pt1      (cdr (assoc 10 entdata))
              pt2      (cdr (assoc 11 entdata)))

        (setq new_pt1 (list (+ (car pt1) move_right) (cadr pt1) (caddr pt1))
              new_pt2 (list (+ (car pt2) move_right) (cadr pt2) (caddr pt2)))

        (if (> (cadr new_pt1) (cadr new_pt2))
          (if (> dy 0)
            (setq new_pt1 (list (car new_pt1) (+ (cadr new_pt1) 5.0) (caddr new_pt1)))
            (setq new_pt2 (list (car new_pt2) (- (cadr new_pt2) 5.0) (caddr new_pt2))))
          (if (> dy 0)
            (setq new_pt2 (list (car new_pt2) (+ (cadr new_pt2) 5.0) (caddr new_pt2)))
            (setq new_pt1 (list (car new_pt1) (- (cadr new_pt1) 5.0) (caddr new_pt1))))
        )

        (setq entdata (subst (cons 10 new_pt1) (assoc 10 entdata) entdata))
        (setq entdata (subst (cons 11 new_pt2) (assoc 11 entdata) entdata))
        (entmod entdata)
      )

      ;; 7. 处理斜线：复制 → 右移 move_right → 上/下移 5
      (foreach ent diag_lines
        (setq copy_ent (entmakex (entget ent))
              entdata  (entget copy_ent)
              pt1      (cdr (assoc 10 entdata))
              pt2      (cdr (assoc 11 entdata)))

        (setq new_pt1 (list (+ (car pt1) move_right) (+ (cadr pt1) dy) (caddr pt1))
              new_pt2 (list (+ (car pt2) move_right) (+ (cadr pt2) dy) (caddr pt2)))

        (setq entdata (subst (cons 10 new_pt1) (assoc 10 entdata) entdata))
        (setq entdata (subst (cons 11 new_pt2) (assoc 11 entdata) entdata))
        (entmod entdata)
      )

      ;; 8. 处理水平直线：复制 → 上/下移 5 → 左端缩短 move_right（右端不动）
      (foreach ent horiz_lines
        (setq copy_ent (entmakex (entget ent))
              entdata  (entget copy_ent)
              pt1      (cdr (assoc 10 entdata))
              pt2      (cdr (assoc 11 entdata)))

        (if (< (car pt1) (car pt2))
          (setq new_pt1 (list (+ (car pt1) move_right) (+ (cadr pt1) dy) (caddr pt1))
                new_pt2 (list (car pt2)                 (+ (cadr pt2) dy) (caddr pt2)))
          (setq new_pt1 (list (car pt1)                 (+ (cadr pt1) dy) (caddr pt1))
                new_pt2 (list (+ (car pt2) move_right)  (+ (cadr pt2) dy) (caddr pt2)))
        )

        (setq entdata (subst (cons 10 new_pt1) (assoc 10 entdata) entdata))
        (setq entdata (subst (cons 11 new_pt2) (assoc 11 entdata) entdata))
        (entmod entdata)
      )

      ;; 9. 完成提示
      (princ
        (strcat "\n完成！所有对象已原地复制。"
                "\n副本：竖直线 & 斜线右移 " (rtos move_right 2 0)
                " 单位 + " (if (> dy 0) "向上" "向下") " 5 单位；"
                "\n      水平线 " (if (> dy 0) "向上" "向下")
                " 5 单位 + 左端缩短 " (rtos move_right 2 0) " 单位（右端不动）。"))
      (princ)
    )

    (defun c:XIN ( / ss i ent entData pt1 pt2 leftX rightX topY bottomY
                    countSS countNum insertPt textStr rightPt)
      (setq ss (ssget '((0 . "LINE"))))
      (if (null ss)
        (progn
          (alert "未选择任何直线！")
          (exit)
        )
      )

      (setq i 0)
      (while (< i (sslength ss))
        (setq ent (ssname ss i))
        (setq entData (entget ent))

        (setq pt1 (cdr (assoc 10 entData)))
        (setq pt2 (cdr (assoc 11 entData)))

        (if (< (car pt1) (car pt2))
          (progn
            (setq leftX (car pt1))
            (setq rightX (car pt2))
            (setq rightPt pt2)
          )
          (progn
            (setq leftX (car pt2))
            (setq rightX (car pt1))
            (setq rightPt pt1)
          )
        )

        (setq topY (+ (cadr pt1) 1.6))
        (setq bottomY (- (cadr pt1) 1.6))

        (setq countSS
               (ssget "W"
                 (list leftX bottomY 0.0)
                 (list rightX topY 0.0)
               )
        )

        (if countSS
          (progn
            (setq countNum (sslength countSS))
            (if (ssmemb ent countSS)
              (progn
                (ssdel ent countSS)
                (setq countNum (1- countNum))
              )
            )
          )
          (setq countNum 0)
        )

        (setq insertPt (list (+ (car rightPt) 2) (+ (cadr rightPt) 0.5) 0.0))
        (setq textStr (itoa countNum))

        (entmake
          (list
            (cons 0 "TEXT")
            (cons 10 insertPt)
            (cons 40 3.0)
            (cons 1 textStr)
            (cons 7 "Standard")
            (cons 50 0.0)
          )
        )

        (setq i (1+ i))
      )

      (princ (strcat "\n处理完成，共处理 " (itoa (sslength ss)) " 条直线。"))
      (princ)
    )

    (setq *ys-module-cable_tools-loaded* T)
    (princ "\n[YS-Tools] cable-tools.lsp loaded.")
  )
)
(princ)
;;; ----- END YS-Tools/modules/cable-tools.lsp -----

;;; ----- BEGIN YS-Tools/modules/xy-tools.lsp -----
;;; YS-Tools v1.5.0 module
;;; Encoding: GBK/ANSI, CRLF

(if (and (boundp '*ys-module-xy_tools-loaded*)
         *ys-module-xy_tools-loaded*)
  (princ)
  (progn
    (vl-catch-all-apply 'vl-load-com '())

    (defun xy:abs (x)
      (if (< x 0.0) (- x) x)
    )

    (defun xy:near (a b tol)
      (<= (xy:abs (- a b)) tol)
    )

    (defun xy:between (v a b tol)
      (and (>= v (- (min a b) tol))
           (<= v (+ (max a b) tol)))
    )

    (defun xy:ss->list (ss / i lst)
      (setq lst '())
      (if ss
        (progn
          (setq i 0)
          (while (< i (sslength ss))
            (setq lst (cons (ssname ss i) lst))
            (setq i (1+ i))
          )
        )
      )
      (reverse lst)
    )

    (defun xy:get-line-pts (en / ed p1 p2)
      (setq ed (entget en))
      (setq p1 (cdr (assoc 10 ed)))
      (setq p2 (cdr (assoc 11 ed)))
      (list p1 p2)
    )

    (defun xy:is-line-p (en)
      (= (cdr (assoc 0 (entget en))) "LINE")
    )

    (defun xy:is-horizontal-line-p (en tol / pts p1 p2)
      (if (not (xy:is-line-p en))
        nil
        (progn
          (setq pts (xy:get-line-pts en))
          (setq p1 (car pts))
          (setq p2 (cadr pts))
          (xy:near (cadr p1) (cadr p2) tol)
        )
      )
    )

    (defun xy:is-vertical-line-p (en tol / pts p1 p2)
      (if (not (xy:is-line-p en))
        nil
        (progn
          (setq pts (xy:get-line-pts en))
          (setq p1 (car pts))
          (setq p2 (cadr pts))
          (xy:near (car p1) (car p2) tol)
        )
      )
    )

    (defun xy:is-vertical-line-ed-p (ed tol / p1 p2)
      (and (= (cdr (assoc 0 ed)) "LINE")
           (setq p1 (cdr (assoc 10 ed)))
           (setq p2 (cdr (assoc 11 ed)))
           (xy:near (car p1) (car p2) tol))
    )

    (defun xy:right-endpoint (en / pts p1 p2)
      (setq pts (xy:get-line-pts en))
      (setq p1 (car pts))
      (setq p2 (cadr pts))
      (if (>= (car p1) (car p2)) p1 p2)
    )

    (defun xy:pt-offset-x (pt dx)
      (cons (+ (car pt) dx) (cdr pt))
    )

    (defun xy:remove-dxf-codes (ed codes)
      (vl-remove-if
        '(lambda (pair) (member (car pair) codes))
        ed)
    )

    (defun xy:mark-abnormal-hline (en / ed p1 p2 newPt)
      (setq ed (entget en))
      (setq p1 (cdr (assoc 10 ed)))
      (setq p2 (cdr (assoc 11 ed)))
      (if (and p1 p2)
        (progn
          (if (>= (car p1) (car p2))
            (progn
              (setq newPt (xy:pt-offset-x p1 *xy-warn-extend-len*))
              (setq ed (subst (cons 10 newPt) (assoc 10 ed) ed))
            )
            (progn
              (setq newPt (xy:pt-offset-x p2 *xy-warn-extend-len*))
              (setq ed (subst (cons 11 newPt) (assoc 11 ed) ed))
            )
          )
          (setq ed (xy:remove-dxf-codes ed '(62 420 430 440)))
          (entmod (append ed (list (cons 62 1))))
          (entupd en)
        )
      )
    )

    (defun xy:hline-info (en / pts p1 p2 x1 x2 y rightpt)
      (setq pts (xy:get-line-pts en))
      (setq p1 (car pts))
      (setq p2 (cadr pts))
      (setq x1 (car p1))
      (setq x2 (car p2))
      (setq y  (cadr p1))
      (setq rightpt (xy:right-endpoint en))
      (list (min x1 x2) (max x1 x2) y rightpt)
    )

    (defun xy:norm-angle (a)
      (while (< a 0.0)
        (setq a (+ a (* 2.0 pi)))
      )
      (while (>= a (* 2.0 pi))
        (setq a (- a (* 2.0 pi)))
      )
      a
    )

    (defun xy:is-vertical-text-90-p (ang tol / a)
      (setq a (xy:norm-angle ang))
      (<= (xy:abs (- a (/ pi 2.0))) tol)
    )

    (defun xy:dxf (code ed default / pair)
      (setq pair (assoc code ed))
      (if pair (cdr pair) default)
    )

    (defun xy:is-text-entity-p (en / typ)
      (setq typ (cdr (assoc 0 (entget en))))
      (or (= typ "TEXT") (= typ "MTEXT"))
    )

    (defun xy:get-text-rotation (ed)
      (xy:dxf 50 ed 0.0)
    )

    (defun xy:get-text-height (ed)
      (xy:dxf 40 ed 3.0)
    )

    (defun xy:get-text-style (ed)
      (xy:dxf 7 ed "Standard")
    )

    (defun xy:get-text-value (ed)
      (xy:dxf 1 ed "")
    )

    (defun xy:filter-vertical-lines (lineList / out en ed p1 p2)
      (setq out '())
      (foreach en lineList
        (setq ed (entget en))
        (if (xy:is-vertical-line-ed-p ed *xy-geom-tol*)
          (progn
            (setq p1 (cdr (assoc 10 ed)))
            (setq p2 (cdr (assoc 11 ed)))
            (setq out (cons (list en (car p1) (cadr p1) (cadr p2)) out))
          )
        )
      )
      (reverse out)
    )

    (defun xy:get-vrecs-for-hline (hen vlineDataList / handle pair hinfo vrecs vdata vrec)
      (setq handle (cdr (assoc 5 (entget hen))))
      (setq pair (assoc handle *xy-last-vrec-map*))
      (if pair
        (cdr pair)
        (progn
          (setq hinfo (xy:hline-info hen))
          (setq vrecs '())
          (foreach vdata vlineDataList
            (setq vrec (xy:make-vrec-if-valid-fast vdata hinfo *xy-geom-tol*))
            (if vrec
              (setq vrecs (cons vrec vrecs))
            )
          )
          (xy:dedup-vrecs vrecs *xy-geom-tol*)
        )
      )
    )

    (defun xy:count-vlines-for-hline (hen lineList)
      (length (xy:get-vrecs-for-hline hen lineList))
    )

    (defun xy:run-xin (sel / selList lineSS vlineDataList ss i ent entData rightPt handle countMap vrecMap vrecs countNum insertPt textStr)
      (setq *xy-last-xin-counts* nil)
      (setq *xy-last-vrec-map* nil)
      (setq *xy-last-vline-data* nil)
      (setq selList  (xy:ss->list sel))
      (setq lineSS   (ssget "_X" '((0 . "LINE"))))
      (setq vlineDataList (xy:filter-vertical-lines (xy:ss->list lineSS)))
      (setq *xy-last-vline-data* vlineDataList)
      (setq ss (ssadd))
      (foreach ent selList
        (if (xy:is-horizontal-line-p ent *xy-geom-tol*)
          (ssadd ent ss)
        )
      )
      (if (= (sslength ss) 0)
        (progn
          (princ "\n选集中没有可供XIN处理的水平直线。")
          nil
        )
        (progn
          (setq i 0)
          (setq countMap '())
          (setq vrecMap '())
          (while (< i (sslength ss))
            (setq ent     (ssname ss i))
            (setq entData (entget ent))
            (setq rightPt (xy:right-endpoint ent))
            (setq vrecs (xy:get-vrecs-for-hline ent vlineDataList))
            (setq countNum (length vrecs))

            (setq handle   (cdr (assoc 5 entData)))
            (setq countMap (cons (cons handle countNum) countMap))
            (setq vrecMap  (cons (cons handle vrecs) vrecMap))
            (setq insertPt (list (+ (car rightPt) 2) (+ (cadr rightPt) 0.5) 0.0))
            (setq textStr (itoa countNum))

            (entmake
              (list
                (cons 0 "TEXT")
                (cons 10 insertPt)
                (cons 40 3.0)
                (cons 1 textStr)
                (cons 7 "Standard")
                (cons 50 0.0)
              )
            )

            (setq i (1+ i))
          )

          (setq *xy-last-xin-counts* (reverse countMap))
          (setq *xy-last-vrec-map*   (reverse vrecMap))
          (princ (strcat "\nXIN处理完成，共处理 " (itoa (sslength ss)) " 条水平直线。"))
          T
        )
      )
    )

    (defun xy:make-vrec-if-valid (ven hinfo tol / pts p1 p2 x y1 y2 hy xmin xmax lo hi)
      (if (not (xy:is-vertical-line-p ven tol))
        nil
        (progn
          (setq pts  (xy:get-line-pts ven))
          (setq p1   (car pts))
          (setq p2   (cadr pts))
          (setq x    (car p1))
          (setq y1   (cadr p1))
          (setq y2   (cadr p2))
          (setq xmin (car hinfo))
          (setq xmax (cadr hinfo))
          (setq hy   (caddr hinfo))
          (setq lo   (if (< y1 y2) p1 p2))
          (setq hi   (if (> y1 y2) p1 p2))

          (if (not (xy:between x xmin xmax tol))
            nil
            (cond
              ((and (xy:near (cadr hi) hy tol)
                    (< (cadr lo) (- hy tol)))
               (list x 'DOWN lo ven)
              )
              ((and (xy:near (cadr lo) hy tol)
                    (> (cadr hi) (+ hy tol)))
               (list x 'UP hi ven)
              )
              (t nil)
            )
          )
        )
      )
    )

    (defun xy:make-vrec-if-valid-fast (vdata hinfo tol / en x y1 y2 xmin xmax hy loY hiY)
      (setq en   (car vdata))
      (setq x    (cadr vdata))
      (setq y1   (caddr vdata))
      (setq y2   (cadddr vdata))
      (setq xmin (car hinfo))
      (setq xmax (cadr hinfo))
      (setq hy   (caddr hinfo))

      (if (not (xy:between x xmin xmax tol))
        nil
        (progn
          (setq loY (min y1 y2))
          (setq hiY (max y1 y2))
          (cond
            ((and (xy:near hiY hy tol)
                  (< loY (- hy tol)))
             (list x 'DOWN (list x loY 0.0) en))
            ((and (xy:near loY hy tol)
                  (> hiY (+ hy tol)))
             (list x 'UP   (list x hiY 0.0) en))
            (t nil)
          )
        )
      )
    )

    (defun xy:merge-vrec (a b / side pa pb)
      (setq side (cadr a))
      (setq pa   (caddr a))
      (setq pb   (caddr b))
      (cond
        ((eq side 'DOWN)
         (if (< (cadr pa) (cadr pb)) a b)
        )
        ((eq side 'UP)
         (if (> (cadr pa) (cadr pb)) a b)
        )
        (t a)
      )
    )

    (defun xy:dedup-vrecs (lst tol / sorted out rec top)
      (setq sorted
            (vl-sort lst
              '(lambda (a b) (< (car a) (car b)))
            )
      )
      (setq out '())
      (foreach rec sorted
        (if (null out)
          (setq out (list rec))
          (progn
            (setq top (car out))
            (if (and (xy:near (car rec) (car top) tol)
                     (eq (cadr rec) (cadr top)))
              (setq out (cons (xy:merge-vrec rec top) (cdr out)))
              (setq out (cons rec out))
            )
          )
        )
      )
      (reverse out)
    )

    (defun xy:sa->list (val)
      (vlax-safearray->list
        (if (= (type val) 'VARIANT)
          (vlax-variant-value val)
          val))
    )

    (defun xy:fallback-text-bbox (ed / ip h txt w)
      (setq ip  (xy:dxf 10 ed '(0.0 0.0 0.0)))
      (setq h   (xy:get-text-height ed))
      (setq txt (xy:get-text-value ed))
      (setq w   (max h (* (strlen txt) h 0.7)))
      (list (- (car ip) (/ h 2.0))
            (+ (car ip) (/ h 2.0))
            (- (cadr ip) (/ w 2.0))
            (+ (cadr ip) (/ w 2.0)))
    )

    (defun xy:get-text-bbox (en / ed obj minPt maxPt ret minLst maxLst)
      (setq ed (entget en))
      (if (xy:is-text-entity-p en)
        (progn
          (setq obj (vlax-ename->vla-object en))
          (setq ret (vl-catch-all-apply 'vla-getBoundingBox (list obj 'minPt 'maxPt)))
          (if (vl-catch-all-error-p ret)
            (xy:fallback-text-bbox ed)
            (progn
              (setq minLst (xy:sa->list minPt))
              (setq maxLst (xy:sa->list maxPt))
              (list (car minLst) (car maxLst) (cadr minLst) (cadr maxLst))
            )
          )
        )
        nil
      )
    )

    (defun xy:build-text-meta-list (textList / out en ed rot bbox)
      (setq out '())
      (foreach en textList
        (setq ed (entget en))
        (if (xy:is-text-entity-p en)
          (progn
            (setq rot (xy:get-text-rotation ed))
            (if (xy:is-vertical-text-90-p rot *xy-ang-tol*)
              (progn
                (setq bbox (xy:get-text-bbox en))
                (if bbox
                  (setq out
                        (cons
                          (list en
                                (car bbox)
                                (cadr bbox)
                                (caddr bbox)
                                (cadddr bbox)
                                rot)
                          out))
                )
              )
            )
          )
        )
      )
      (reverse out)
    )

    (defun xy:find-text-for-vrec (textMetaList vrec / side anchor ax ay rectXmin rectXmax rectYmin rectYmax best bestHit bestXDist item en xmin xmax ymin ymax hitY xCenter xDist)
      (setq side   (cadr vrec))
      (setq anchor (caddr vrec))
      (setq ax     (car anchor))
      (setq ay     (cadr anchor))

      (cond
        ((eq side 'DOWN)
         (setq rectXmin (- ax *xy-hit-half-width*))
         (setq rectXmax (+ ax *xy-hit-half-width*))
         (setq rectYmin (- ay *xy-ray-len*))
         (setq rectYmax ay)
         (setq best nil)
         (setq bestHit nil)
         (setq bestXDist nil)

         (foreach item textMetaList
           (setq en   (car item))
           (setq xmin (cadr item))
           (setq xmax (caddr item))
           (setq ymin (cadddr item))
           (setq ymax (nth 4 item))
           (if (and (<= xmin (+ rectXmax *xy-geom-tol*))
                    (>= xmax (- rectXmin *xy-geom-tol*))
                    (<= ymin (+ rectYmax *xy-geom-tol*))
                    (>= ymax (- rectYmin *xy-geom-tol*)))
             (progn
               (setq hitY (min rectYmax ymax))
               (setq xCenter (/ (+ xmin xmax) 2.0))
               (setq xDist (xy:abs (- xCenter ax)))
               (if (or (null best)
                       (> hitY (+ bestHit *xy-geom-tol*))
                       (and (xy:near hitY bestHit *xy-geom-tol*)
                            (< xDist bestXDist)))
                 (progn
                   (setq best      en)
                   (setq bestHit   hitY)
                   (setq bestXDist xDist)
                 )
               )
             )
           )
         )
         best
        )
        ((eq side 'UP)
         (setq rectXmin (- ax *xy-hit-half-width*))
         (setq rectXmax (+ ax *xy-hit-half-width*))
         (setq rectYmin ay)
         (setq rectYmax (+ ay *xy-ray-len*))
         (setq best nil)
         (setq bestHit nil)
         (setq bestXDist nil)

         (foreach item textMetaList
           (setq en   (car item))
           (setq xmin (cadr item))
           (setq xmax (caddr item))
           (setq ymin (cadddr item))
           (setq ymax (nth 4 item))
           (if (and (<= xmin (+ rectXmax *xy-geom-tol*))
                    (>= xmax (- rectXmin *xy-geom-tol*))
                    (<= ymin (+ rectYmax *xy-geom-tol*))
                    (>= ymax (- rectYmin *xy-geom-tol*)))
             (progn
               (setq hitY (max rectYmin ymin))
               (setq xCenter (/ (+ xmin xmax) 2.0))
               (setq xDist (xy:abs (- xCenter ax)))
               (if (or (null best)
                       (< hitY (- bestHit *xy-geom-tol*))
                       (and (xy:near hitY bestHit *xy-geom-tol*)
                            (< xDist bestXDist)))
                 (progn
                   (setq best      en)
                   (setq bestHit   hitY)
                   (setq bestXDist xDist)
                 )
               )
             )
           )
         )
         best
        )
        (t nil)
      )
    )

    (defun xy:copy-text-horizontal (srcEn insPt / ed data)
      (setq ed (entget srcEn))
      (setq data
        (list
          '(0 . "TEXT")
          (cons 8  (xy:dxf 8 ed "0"))
          (cons 10 insPt)
          (cons 40 (xy:get-text-height ed))
          (cons 1  (xy:get-text-value ed))
          (cons 7  (xy:get-text-style ed))
          (cons 50 0.0)
          (cons 72 0)
          (cons 73 0)
          (cons 210 (xy:dxf 210 ed '(0.0 0.0 1.0)))
        )
      )

      (if (assoc 41 ed)
        (setq data (append data (list (assoc 41 ed))))
      )
      (if (assoc 51 ed)
        (setq data (append data (list (assoc 51 ed))))
      )
      (if (assoc 39 ed)
        (setq data (append data (list (assoc 39 ed))))
      )
      (if (assoc 62 ed)
        (setq data (append data (list (assoc 62 ed))))
      )
      (if (assoc 420 ed)
        (setq data (append data (list (assoc 420 ed))))
      )

      (entmakex data)
    )

    (defun xy:process-one-hline (hen vlineDataList textMetaList / hinfo vrecs found txt rightPt startPt idx newCnt missCnt allVCnt)
      (setq hinfo (xy:hline-info hen))
      (setq vrecs (xy:get-vrecs-for-hline hen vlineDataList))
      (setq allVCnt (length vrecs))
      (setq found   '())
      (setq missCnt 0)

      (foreach vrec vrecs
        (setq txt (xy:find-text-for-vrec textMetaList vrec))
        (if txt
          (setq found (cons (list (car vrec) txt) found))
          (setq missCnt (1+ missCnt))
        )
      )

      (setq found
            (vl-sort found
              '(lambda (a b) (< (car a) (car b)))
            )
      )

      (setq rightPt (cadddr hinfo))
      (setq startPt
            (list (+ (car rightPt) *xy-out-offx*)
                  (+ (cadr rightPt) *xy-out-offy*)
                  (if (caddr rightPt) (caddr rightPt) 0.0))
      )

      (setq idx 0)
      (setq newCnt 0)

      (foreach item found
        (xy:copy-text-horizontal
          (cadr item)
          (list (+ (car startPt) (* idx *xy-step-x*))
                (cadr startPt)
                (caddr startPt))
        )
        (setq idx    (1+ idx))
        (setq newCnt (1+ newCnt))
      )

      (list newCnt missCnt allVCnt)
    )

    (defun xy:run-yuan (sel / selList lineSS textSS vlineDataList textList textMetaList hLines en res totalH totalNew totalMiss totalV handle ed warnCnt hY warnYText)
      (if (null sel)
        (progn
          (princ "\n未选择对象，YUAN部分结束。")
          nil
        )
        (progn
          (if *xy-last-vline-data*
            (setq vlineDataList *xy-last-vline-data*)
            (progn
              (setq lineSS (ssget "_X" '((0 . "LINE"))))
              (setq vlineDataList (xy:filter-vertical-lines (xy:ss->list lineSS)))
            )
          )
          (setq textSS   (ssget "_X" '((0 . "TEXT,MTEXT"))))
          (setq textList (xy:ss->list textSS))
          (setq textMetaList (xy:build-text-meta-list textList))
          (setq selList  (xy:ss->list sel))

          (setq hLines '())
          (foreach en selList
            (if (xy:is-horizontal-line-p en *xy-geom-tol*)
              (setq hLines (cons en hLines))
            )
          )
          (setq hLines (reverse hLines))

          (if (null hLines)
            (progn
              (princ "\n选集中没有可处理的水平 LINE，YUAN部分结束。")
              nil
            )
            (progn
              (setq totalH    0)
              (setq totalNew  0)
              (setq totalMiss 0)
              (setq totalV    0)
              (setq warnCnt   0)
              (setq warnYText "")

              (foreach en hLines
                (setq res (xy:process-one-hline en vlineDataList textMetaList))
                (setq totalH    (1+ totalH))
                (setq totalNew  (+ totalNew  (car res)))
                (setq totalMiss (+ totalMiss (cadr res)))
                (setq totalV    (+ totalV    (caddr res)))

                (setq ed      (entget en))
                (setq handle  (cdr (assoc 5 ed)))
                (setq hY      (caddr (xy:hline-info en)))

                (princ
                  (strcat
                    "\n水平线 Handle="
                    handle
                    " | 竖线数="
                    (itoa (caddr res))
                    " | 成功="
                    (itoa (car res))
                    " | 未找到文字="
                    (itoa (cadr res))
                  )
                )

                (if (/= (car res) (caddr res))
                  (progn
                    (xy:mark-abnormal-hline en)
                    (setq warnCnt (1+ warnCnt))
                    (setq warnYText
                          (if (= warnYText "")
                            (rtos hY 2 4)
                            (strcat warnYText ", " (rtos hY 2 4))))
                    (princ
                      (strcat
                        "\n警告: 水平线 Handle="
                        handle
                        "，Y="
                        (rtos hY 2 4)
                        " 找到文字="
                        (itoa (car res))
                        "，竖线数="
                        (itoa (caddr res))
                        "。异常请检查。"
                      )
                    )
                  )
                )
              )

              (princ
                (strcat
                  "\n--- YUAN 执行完成 ---"
                  "\n处理水平线数量: " (itoa totalH)
                  "\n识别竖线总数: "   (itoa totalV)
                  "\n新建文字总数: "   (itoa totalNew)
                  "\n未找到文字总数: " (itoa totalMiss)
                )
              )
              (if (> warnCnt 0)
                (princ
                  (strcat
                    "\n注意: 发现 "
                    (itoa warnCnt)
                    " 条水平线的找到文字数与竖线数不一致，请检查对应水平线。"
                    "\n异常水平线Y坐标汇总: "
                    warnYText
                  )
                )
              )
              T
            )
          )
        )
      )
    )

    (defun c:XY (/ sel)
      (princ "\n选择对象，XY会共用这一批对象执行XIN和YUAN: ")
      (setq sel (ssget))
      (if (null sel)
        (princ "\n未选择对象，XY命令结束。")
        (progn
          (princ "\n开始执行 XY：先运行 XIN，再运行 YUAN。")
          (xy:run-xin sel)
          (xy:run-yuan sel)
          (princ "\nXY 执行结束。")
        )
      )
      (princ)
    )

    (setq *ys-module-xy_tools-loaded* T)
    (princ "\n[YS-Tools] xy-tools.lsp loaded.")
  )
)
(princ)
;;; ----- END YS-Tools/modules/xy-tools.lsp -----
